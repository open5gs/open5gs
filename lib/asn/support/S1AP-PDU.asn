-- **************************************************************
--
-- Elementary Procedure definitions
--
-- **************************************************************


S1AP-PDU-Descriptions  { 
itu-t (0) identified-organization (4) etsi (0) mobileDomain (0) 
eps-Access (21) modules (3) s1ap (1) version1 (1) s1ap-PDU-Descriptions (0)}


DEFINITIONS AUTOMATIC TAGS ::= 


BEGIN


-- **************************************************************
--
-- IE parameter types from other modules.
--
-- **************************************************************


IMPORTS
        S1ap-Criticality,
        S1ap-ProcedureCode
FROM S1AP-CommonDataTypes


        S1ap-CellTrafficTrace,
        S1ap-DeactivateTrace,
        S1ap-DownlinkUEAssociatedLPPaTransport,
        S1ap-DownlinkNASTransport,
        S1ap-DownlinkNonUEAssociatedLPPaTransport,
        S1ap-DownlinkS1cdma2000tunneling,
        S1ap-ENBDirectInformationTransfer,
        S1ap-ENBStatusTransfer,
        S1ap-ENBConfigurationUpdate,
        S1ap-ENBConfigurationUpdateAcknowledge,
        S1ap-ENBConfigurationUpdateFailure,
        S1ap-ErrorIndication,
        S1ap-HandoverCancel,
        S1ap-HandoverCancelAcknowledge,
        S1ap-HandoverCommand,
        S1ap-HandoverFailure,
        S1ap-HandoverNotify,
        S1ap-HandoverPreparationFailure,
        S1ap-HandoverRequest,
        S1ap-HandoverRequestAcknowledge,
        S1ap-HandoverRequired,
        S1ap-InitialContextSetupFailure,
        S1ap-InitialContextSetupRequest,
        S1ap-InitialContextSetupResponse,
        S1ap-InitialUEMessage,
        S1ap-KillRequest,
        S1ap-KillResponse,
        S1ap-LocationReportingControl,
        S1ap-LocationReportingFailureIndication,
        S1ap-LocationReport,
        S1ap-MMEConfigurationUpdate,
        S1ap-MMEConfigurationUpdateAcknowledge,
        S1ap-MMEConfigurationUpdateFailure,
        S1ap-MMEDirectInformationTransfer,
        S1ap-MMEStatusTransfer,
        S1ap-NASNonDeliveryIndication,
        S1ap-OverloadStart,
        S1ap-OverloadStop,
        S1ap-Paging,
        S1ap-PathSwitchRequest,
        S1ap-PathSwitchRequestAcknowledge,
        S1ap-PathSwitchRequestFailure,        
        S1ap-PrivateMessage,
        S1ap-Reset,
        S1ap-ResetAcknowledge,
        S1ap-S1SetupFailure,
        S1ap-S1SetupRequest,
        S1ap-S1SetupResponse,
        S1ap-E-RABModifyRequest,
        S1ap-E-RABModifyResponse,
        S1ap-E-RABReleaseCommand,
        S1ap-E-RABReleaseResponse,
        S1ap-E-RABReleaseIndication,
        S1ap-E-RABSetupRequest,
        S1ap-E-RABSetupResponse,
        S1ap-TraceFailureIndication,
        S1ap-TraceStart,
        S1ap-UECapabilityInfoIndication,
        S1ap-UEContextModificationFailure,
        S1ap-UEContextModificationRequest,
        S1ap-UEContextModificationResponse,
        S1ap-UEContextReleaseCommand,
        S1ap-UEContextReleaseComplete,
        S1ap-UEContextReleaseRequest,
        S1ap-UplinkUEAssociatedLPPaTransport,
        S1ap-UplinkNASTransport,
        S1ap-UplinkNonUEAssociatedLPPaTransport,
        S1ap-UplinkS1cdma2000tunneling,
        S1ap-WriteReplaceWarningRequest,
        S1ap-WriteReplaceWarningResponse,
        S1ap-ENBConfigurationTransfer,
        S1ap-MMEConfigurationTransfer




FROM S1AP-PDU-Contents
        
        id-CellTrafficTrace,
        id-DeactivateTrace,
        id-downlinkUEAssociatedLPPaTransport,
        id-downlinkNASTransport,
        id-downlinkNonUEAssociatedLPPaTransport,
        id-DownlinkS1cdma2000tunneling,
        id-eNBStatusTransfer,
        id-ErrorIndication,
        id-HandoverCancel,
        id-HandoverNotification,
        id-HandoverPreparation,
        id-HandoverResourceAllocation,
        id-InitialContextSetup,
        id-initialUEMessage,
        id-ENBConfigurationUpdate,
        id-Kill,
        id-LocationReportingControl,
        id-LocationReportingFailureIndication,
        id-LocationReport,
        id-eNBDirectInformationTransfer,
        id-MMEConfigurationUpdate,
        id-MMEDirectInformationTransfer,
        id-MMEStatusTransfer,
        id-NASNonDeliveryIndication,
        id-OverloadStart,
        id-OverloadStop,
        id-Paging,
        id-PathSwitchRequest,
        id-PrivateMessage,
        id-Reset,
        id-S1Setup,
        id-E-RABModify,
        id-E-RABRelease,
        id-E-RABReleaseIndication,
        id-E-RABSetup,
        id-TraceFailureIndication,
        id-TraceStart,
        id-UECapabilityInfoIndication,
        id-UEContextModification,
        id-UEContextRelease,
        id-UEContextReleaseRequest,
        id-uplinkUEAssociatedLPPaTransport,
        id-uplinkNASTransport,
        id-uplinkNonUEAssociatedLPPaTransport,
        id-UplinkS1cdma2000tunneling,
        id-WriteReplaceWarning,
        id-eNBConfigurationTransfer,
        id-MMEConfigurationTransfer
FROM S1AP-Constants;




-- **************************************************************
--
-- Interface Elementary Procedure Class
--
-- **************************************************************


S1AP-ELEMENTARY-PROCEDURE ::= CLASS {
        &S1ap-InitiatingMessage                                ,
        &S1ap-SuccessfulOutcome                                OPTIONAL,
        &S1ap-UnsuccessfulOutcome                                OPTIONAL,
        &procedureCode                        S1ap-ProcedureCode         UNIQUE,
        &criticality                        S1ap-Criticality         DEFAULT ignore
}
WITH SYNTAX {
        INITIATING MESSAGE                        &S1ap-InitiatingMessage
        [SUCCESSFUL OUTCOME                        &S1ap-SuccessfulOutcome]
        [UNSUCCESSFUL OUTCOME                &S1ap-UnsuccessfulOutcome]
        PROCEDURE CODE                                &procedureCode
        [CRITICALITY                                &criticality]
}


-- **************************************************************
--
-- Interface PDU Definition
--
-- **************************************************************


S1AP-PDU ::= CHOICE {
        initiatingMessage        S1ap-InitiatingMessage,
        successfulOutcome        S1ap-SuccessfulOutcome,
        unsuccessfulOutcome        S1ap-UnsuccessfulOutcome,
        ...
}


S1ap-InitiatingMessage ::= SEQUENCE {
        procedureCode        S1AP-ELEMENTARY-PROCEDURE.&procedureCode        ({S1AP-ELEMENTARY-PROCEDURES}),
        criticality        S1AP-ELEMENTARY-PROCEDURE.&criticality                        ({S1AP-ELEMENTARY-PROCEDURES}{@procedureCode}),
        value                S1AP-ELEMENTARY-PROCEDURE.&S1ap-InitiatingMessage        ({S1AP-ELEMENTARY-PROCEDURES}{@procedureCode})
}


S1ap-SuccessfulOutcome ::= SEQUENCE {
        procedureCode        S1AP-ELEMENTARY-PROCEDURE.&procedureCode        ({S1AP-ELEMENTARY-PROCEDURES}),
        criticality        S1AP-ELEMENTARY-PROCEDURE.&criticality                        ({S1AP-ELEMENTARY-PROCEDURES}{@procedureCode}),
        value                S1AP-ELEMENTARY-PROCEDURE.&S1ap-SuccessfulOutcome        ({S1AP-ELEMENTARY-PROCEDURES}{@procedureCode})
}


S1ap-UnsuccessfulOutcome ::= SEQUENCE {
        procedureCode        S1AP-ELEMENTARY-PROCEDURE.&procedureCode        ({S1AP-ELEMENTARY-PROCEDURES}),
        criticality        S1AP-ELEMENTARY-PROCEDURE.&criticality                        ({S1AP-ELEMENTARY-PROCEDURES}{@procedureCode}),
        value                S1AP-ELEMENTARY-PROCEDURE.&S1ap-UnsuccessfulOutcome        ({S1AP-ELEMENTARY-PROCEDURES}{@procedureCode})
}


-- **************************************************************
--
-- Interface Elementary Procedure List
--
-- **************************************************************


S1AP-ELEMENTARY-PROCEDURES S1AP-ELEMENTARY-PROCEDURE ::= {
        S1AP-ELEMENTARY-PROCEDURES-CLASS-1                |
        S1AP-ELEMENTARY-PROCEDURES-CLASS-2,        
        ...
}




S1AP-ELEMENTARY-PROCEDURES-CLASS-1 S1AP-ELEMENTARY-PROCEDURE ::= {
        handoverPreparation                                |
        handoverResourceAllocation                |
        pathSwitchRequest                                 |
        e-RABSetup                                                |
        e-RABModify                                                |
        e-RABRelease                                        |
        initialContextSetup                                |
        handoverCancel                                        |
        kill                                                        |
        reset                                                        |
        s1Setup                                                        |
        uEContextModification                        |
        uEContextRelease                                |
        eNBConfigurationUpdate                        |
        mMEConfigurationUpdate                        |
        writeReplaceWarning                                ,
        ...
}


S1AP-ELEMENTARY-PROCEDURES-CLASS-2 S1AP-ELEMENTARY-PROCEDURE ::= {        
        handoverNotification                        |
        e-RABReleaseIndication                        |
        paging                                                         |
        downlinkNASTransport                        |
        initialUEMessage                                |
        uplinkNASTransport                                |
        errorIndication                                        |
        nASNonDeliveryIndication                |
        uEContextReleaseRequest                        |
        downlinkS1cdma2000tunneling                |
        uplinkS1cdma2000tunneling                |
        uECapabilityInfoIndication                |
        eNBStatusTransfer                                |
        mMEStatusTransfer                                |
        deactivateTrace                                        |
        traceStart                                                |
        traceFailureIndication                        |
        cellTrafficTrace                                |
        locationReportingControl                |
        locationReportingFailureIndication        |
        locationReport                                        |
        overloadStart                                        |
        overloadStop                                        |
        eNBDirectInformationTransfer        |
        mMEDirectInformationTransfer        |
        eNBConfigurationTransfer                |
        mMEConfigurationTransfer                |
        privateMessage                                        ,
        ...,
        downlinkUEAssociatedLPPaTransport        |
        uplinkUEAssociatedLPPaTransport        |
        downlinkNonUEAssociatedLPPaTransport        |
        uplinkNonUEAssociatedLPPaTransport
}


-- **************************************************************
--
-- Interface Elementary Procedures
--
-- **************************************************************


handoverPreparation S1AP-ELEMENTARY-PROCEDURE ::= {
        INITIATING MESSAGE        S1ap-HandoverRequired
        SUCCESSFUL OUTCOME        S1ap-HandoverCommand
        UNSUCCESSFUL OUTCOME        S1ap-HandoverPreparationFailure
        PROCEDURE CODE                        id-HandoverPreparation
        CRITICALITY                reject
}


handoverResourceAllocation S1AP-ELEMENTARY-PROCEDURE ::= {
        INITIATING MESSAGE        S1ap-HandoverRequest
        SUCCESSFUL OUTCOME        S1ap-HandoverRequestAcknowledge
        UNSUCCESSFUL OUTCOME        S1ap-HandoverFailure
        PROCEDURE CODE                        id-HandoverResourceAllocation
        CRITICALITY                reject
}


handoverNotification S1AP-ELEMENTARY-PROCEDURE ::= {
        INITIATING MESSAGE        S1ap-HandoverNotify
        PROCEDURE CODE                        id-HandoverNotification
        CRITICALITY                ignore
}


pathSwitchRequest S1AP-ELEMENTARY-PROCEDURE ::= {
        INITIATING MESSAGE        S1ap-PathSwitchRequest
        SUCCESSFUL OUTCOME        S1ap-PathSwitchRequestAcknowledge
        UNSUCCESSFUL OUTCOME        S1ap-PathSwitchRequestFailure
        PROCEDURE CODE                        id-PathSwitchRequest
        CRITICALITY                reject
}


e-RABSetup S1AP-ELEMENTARY-PROCEDURE ::= {
        INITIATING MESSAGE        S1ap-E-RABSetupRequest
        SUCCESSFUL OUTCOME        S1ap-E-RABSetupResponse
        PROCEDURE CODE                id-E-RABSetup
        CRITICALITY                reject
}


e-RABModify S1AP-ELEMENTARY-PROCEDURE ::= {
        INITIATING MESSAGE        S1ap-E-RABModifyRequest
        SUCCESSFUL OUTCOME        S1ap-E-RABModifyResponse
        PROCEDURE CODE                id-E-RABModify
        CRITICALITY                reject
}


e-RABRelease S1AP-ELEMENTARY-PROCEDURE ::= {
        INITIATING MESSAGE        S1ap-E-RABReleaseCommand
        SUCCESSFUL OUTCOME        S1ap-E-RABReleaseResponse
        PROCEDURE CODE                id-E-RABRelease
        CRITICALITY                reject
}


e-RABReleaseIndication S1AP-ELEMENTARY-PROCEDURE ::= {
        INITIATING MESSAGE        S1ap-E-RABReleaseIndication
        PROCEDURE CODE                id-E-RABReleaseIndication
        CRITICALITY                ignore
}


initialContextSetup S1AP-ELEMENTARY-PROCEDURE ::= {
        INITIATING MESSAGE        S1ap-InitialContextSetupRequest
        SUCCESSFUL OUTCOME        S1ap-InitialContextSetupResponse
        UNSUCCESSFUL OUTCOME S1ap-InitialContextSetupFailure
        PROCEDURE CODE                id-InitialContextSetup
        CRITICALITY                reject
}


uEContextReleaseRequest S1AP-ELEMENTARY-PROCEDURE ::= {
        INITIATING MESSAGE                S1ap-UEContextReleaseRequest
        PROCEDURE CODE                        id-UEContextReleaseRequest
        CRITICALITY                                ignore
}


paging S1AP-ELEMENTARY-PROCEDURE ::= {
        INITIATING MESSAGE        S1ap-Paging
        PROCEDURE CODE                id-Paging
        CRITICALITY                        ignore
}


downlinkNASTransport S1AP-ELEMENTARY-PROCEDURE ::= {
        INITIATING MESSAGE                S1ap-DownlinkNASTransport
        PROCEDURE CODE                        id-downlinkNASTransport
        CRITICALITY                                ignore
}


initialUEMessage S1AP-ELEMENTARY-PROCEDURE ::= {
        INITIATING MESSAGE                S1ap-InitialUEMessage
        PROCEDURE CODE                        id-initialUEMessage
        CRITICALITY                                ignore
}


uplinkNASTransport S1AP-ELEMENTARY-PROCEDURE ::= {
        INITIATING MESSAGE                S1ap-UplinkNASTransport
        PROCEDURE CODE                        id-uplinkNASTransport
        CRITICALITY                                ignore
}
nASNonDeliveryIndication S1AP-ELEMENTARY-PROCEDURE ::= {
        INITIATING MESSAGE                S1ap-NASNonDeliveryIndication
        PROCEDURE CODE                        id-NASNonDeliveryIndication
        CRITICALITY                                ignore
}


handoverCancel S1AP-ELEMENTARY-PROCEDURE ::= {
        INITIATING MESSAGE        S1ap-HandoverCancel
        SUCCESSFUL OUTCOME        S1ap-HandoverCancelAcknowledge
        PROCEDURE CODE                        id-HandoverCancel
        CRITICALITY                reject
}


reset S1AP-ELEMENTARY-PROCEDURE ::= {
        INITIATING MESSAGE        S1ap-Reset
        SUCCESSFUL OUTCOME        S1ap-ResetAcknowledge
        PROCEDURE CODE                id-Reset
        CRITICALITY                        reject
}


errorIndication S1AP-ELEMENTARY-PROCEDURE ::= {
        INITIATING MESSAGE        S1ap-ErrorIndication
        PROCEDURE CODE                id-ErrorIndication
        CRITICALITY                ignore
}


s1Setup S1AP-ELEMENTARY-PROCEDURE ::= {
        INITIATING MESSAGE                S1ap-S1SetupRequest
        SUCCESSFUL OUTCOME                S1ap-S1SetupResponse
        UNSUCCESSFUL OUTCOME         S1ap-S1SetupFailure
        PROCEDURE CODE                        id-S1Setup
        CRITICALITY                                reject
}


eNBConfigurationUpdate S1AP-ELEMENTARY-PROCEDURE ::= {
        INITIATING MESSAGE                S1ap-ENBConfigurationUpdate
        SUCCESSFUL OUTCOME                S1ap-ENBConfigurationUpdateAcknowledge
        UNSUCCESSFUL OUTCOME         S1ap-ENBConfigurationUpdateFailure
        PROCEDURE CODE                        id-ENBConfigurationUpdate
        CRITICALITY                                reject
}


mMEConfigurationUpdate S1AP-ELEMENTARY-PROCEDURE ::= {
        INITIATING MESSAGE                S1ap-MMEConfigurationUpdate
        SUCCESSFUL OUTCOME                S1ap-MMEConfigurationUpdateAcknowledge
        UNSUCCESSFUL OUTCOME         S1ap-MMEConfigurationUpdateFailure
        PROCEDURE CODE                        id-MMEConfigurationUpdate
        CRITICALITY                                reject
}


downlinkS1cdma2000tunneling S1AP-ELEMENTARY-PROCEDURE ::= {
        INITIATING MESSAGE                S1ap-DownlinkS1cdma2000tunneling
        PROCEDURE CODE                        id-DownlinkS1cdma2000tunneling
        CRITICALITY                                ignore
}


uplinkS1cdma2000tunneling S1AP-ELEMENTARY-PROCEDURE ::= {
        INITIATING MESSAGE                S1ap-UplinkS1cdma2000tunneling
        PROCEDURE CODE                        id-UplinkS1cdma2000tunneling
        CRITICALITY                                ignore
}


uEContextModification S1AP-ELEMENTARY-PROCEDURE ::= {
        INITIATING MESSAGE                S1ap-UEContextModificationRequest
        SUCCESSFUL OUTCOME                S1ap-UEContextModificationResponse
        UNSUCCESSFUL OUTCOME         S1ap-UEContextModificationFailure


        PROCEDURE CODE                id-UEContextModification
        CRITICALITY                reject
}


uECapabilityInfoIndication S1AP-ELEMENTARY-PROCEDURE ::= {
        INITIATING MESSAGE                S1ap-UECapabilityInfoIndication
        PROCEDURE CODE                        id-UECapabilityInfoIndication
        CRITICALITY                                ignore
}


uEContextRelease S1AP-ELEMENTARY-PROCEDURE ::= {
        INITIATING MESSAGE                S1ap-UEContextReleaseCommand
        SUCCESSFUL OUTCOME                S1ap-UEContextReleaseComplete
        PROCEDURE CODE                        id-UEContextRelease
        CRITICALITY                                reject
}


eNBStatusTransfer S1AP-ELEMENTARY-PROCEDURE ::= {
        INITIATING MESSAGE                S1ap-ENBStatusTransfer
        PROCEDURE CODE                        id-eNBStatusTransfer
        CRITICALITY                                ignore
}


mMEStatusTransfer S1AP-ELEMENTARY-PROCEDURE ::= {
        INITIATING MESSAGE                S1ap-MMEStatusTransfer
        PROCEDURE CODE                        id-MMEStatusTransfer
        CRITICALITY                                ignore
}


deactivateTrace S1AP-ELEMENTARY-PROCEDURE ::= {
        INITIATING MESSAGE                S1ap-DeactivateTrace
        PROCEDURE CODE                        id-DeactivateTrace
        CRITICALITY                                ignore
}


traceStart S1AP-ELEMENTARY-PROCEDURE ::= {
        INITIATING MESSAGE        S1ap-TraceStart
        PROCEDURE CODE                id-TraceStart
        CRITICALITY                        ignore
}


traceFailureIndication S1AP-ELEMENTARY-PROCEDURE ::= {
        INITIATING MESSAGE        S1ap-TraceFailureIndication
        PROCEDURE CODE                id-TraceFailureIndication
        CRITICALITY                        ignore
}
cellTrafficTrace S1AP-ELEMENTARY-PROCEDURE ::={
     INITIATING MESSAGE S1ap-CellTrafficTrace
     PROCEDURE CODE      id-CellTrafficTrace
     CRITICALITY         ignore
}


locationReportingControl S1AP-ELEMENTARY-PROCEDURE ::= {
        INITIATING MESSAGE                S1ap-LocationReportingControl
        PROCEDURE CODE                        id-LocationReportingControl
        CRITICALITY                                ignore
}


locationReportingFailureIndication S1AP-ELEMENTARY-PROCEDURE ::= {
        INITIATING MESSAGE                S1ap-LocationReportingFailureIndication
        PROCEDURE CODE                        id-LocationReportingFailureIndication
        CRITICALITY                                ignore
}


locationReport S1AP-ELEMENTARY-PROCEDURE ::= {
        INITIATING MESSAGE                S1ap-LocationReport
        PROCEDURE CODE                        id-LocationReport
        CRITICALITY                                ignore
}


overloadStart S1AP-ELEMENTARY-PROCEDURE ::= {
        INITIATING MESSAGE        S1ap-OverloadStart
        PROCEDURE CODE                id-OverloadStart
        CRITICALITY                ignore
}


overloadStop S1AP-ELEMENTARY-PROCEDURE ::= {
        INITIATING MESSAGE        S1ap-OverloadStop
        PROCEDURE CODE                id-OverloadStop
        CRITICALITY                reject
}


writeReplaceWarning S1AP-ELEMENTARY-PROCEDURE ::= {
        INITIATING MESSAGE        S1ap-WriteReplaceWarningRequest
        SUCCESSFUL OUTCOME        S1ap-WriteReplaceWarningResponse
        PROCEDURE CODE                id-WriteReplaceWarning
        CRITICALITY                        reject
}


eNBDirectInformationTransfer S1AP-ELEMENTARY-PROCEDURE ::= {
        INITIATING MESSAGE        S1ap-ENBDirectInformationTransfer
        PROCEDURE CODE                id-eNBDirectInformationTransfer
        CRITICALITY                        ignore
}


mMEDirectInformationTransfer S1AP-ELEMENTARY-PROCEDURE ::= {
        INITIATING MESSAGE        S1ap-MMEDirectInformationTransfer
        PROCEDURE CODE                id-MMEDirectInformationTransfer
        CRITICALITY                        ignore
}


eNBConfigurationTransfer S1AP-ELEMENTARY-PROCEDURE ::= {
        INITIATING MESSAGE                S1ap-ENBConfigurationTransfer
        PROCEDURE CODE                        id-eNBConfigurationTransfer
        CRITICALITY                                ignore
}


mMEConfigurationTransfer S1AP-ELEMENTARY-PROCEDURE ::= {
        INITIATING MESSAGE                S1ap-MMEConfigurationTransfer
        PROCEDURE CODE                        id-MMEConfigurationTransfer
        CRITICALITY                                ignore
}




privateMessage S1AP-ELEMENTARY-PROCEDURE ::= {
        INITIATING MESSAGE        S1ap-PrivateMessage
        PROCEDURE CODE                id-PrivateMessage
        CRITICALITY                        ignore
}


kill S1AP-ELEMENTARY-PROCEDURE ::= {
        INITIATING MESSAGE        S1ap-KillRequest
        SUCCESSFUL OUTCOME        S1ap-KillResponse
        PROCEDURE CODE                id-Kill
        CRITICALITY                        reject
}


downlinkUEAssociatedLPPaTransport S1AP-ELEMENTARY-PROCEDURE ::= {
        INITIATING MESSAGE                S1ap-DownlinkUEAssociatedLPPaTransport
        PROCEDURE CODE                        id-downlinkUEAssociatedLPPaTransport
        CRITICALITY                                ignore
}


uplinkUEAssociatedLPPaTransport S1AP-ELEMENTARY-PROCEDURE ::= {
        INITIATING MESSAGE                S1ap-UplinkUEAssociatedLPPaTransport
        PROCEDURE CODE                        id-uplinkUEAssociatedLPPaTransport
        CRITICALITY                                ignore
}
downlinkNonUEAssociatedLPPaTransport S1AP-ELEMENTARY-PROCEDURE ::= {
        INITIATING MESSAGE                S1ap-DownlinkNonUEAssociatedLPPaTransport
        PROCEDURE CODE                        id-downlinkNonUEAssociatedLPPaTransport
        CRITICALITY                                ignore
}


uplinkNonUEAssociatedLPPaTransport S1AP-ELEMENTARY-PROCEDURE ::= {
        INITIATING MESSAGE                S1ap-UplinkNonUEAssociatedLPPaTransport
        PROCEDURE CODE                        id-uplinkNonUEAssociatedLPPaTransport
        CRITICALITY                                ignore
}


END




-- **************************************************************
--
-- PDU definitions for S1AP.
--
-- **************************************************************


S1AP-PDU-Contents { 
itu-t (0) identified-organization (4) etsi (0) mobileDomain (0) 
eps-Access (21) modules (3) s1ap (1) version1 (1) s1ap-PDU-Contents (1) }


DEFINITIONS AUTOMATIC TAGS ::= 


BEGIN


-- **************************************************************
--
-- IE parameter types from other modules.
--
-- **************************************************************


IMPORTS
        S1ap-Criticality,
        S1ap-Presence,
        S1ap-ProcedureCode
FROM S1AP-CommonDataTypes
        
        S1ap-UEAggregateMaximumBitrate,
        S1ap-Cause,
        S1ap-CellAccessMode,
        S1ap-Cdma2000HORequiredIndication,
        S1ap-Cdma2000HOStatus,
        S1ap-Cdma2000OneXSRVCCInfo,
        S1ap-Cdma2000OneXRAND,
        S1ap-Cdma2000PDU,
        S1ap-Cdma2000RATType,
        S1ap-Cdma2000SectorID,
        S1ap-EUTRANRoundTripDelayEstimationInfo,
        S1ap-CNDomain,
        S1ap-ConcurrentWarningMessageIndicator,
        S1ap-CriticalityDiagnostics,
        S1ap-CSFallbackIndicator,
        S1ap-CSG-Id,
        S1ap-CSG-IdList, 
        S1ap-CSGMembershipStatus,
        S1ap-Data-Forwarding-Not-Possible,
        S1ap-Direct-Forwarding-Path-Availability,
        S1ap-Global-ENB-ID,
        S1ap-EUTRAN-CGI,
        S1ap-ENBname,
        S1ap-ENB-StatusTransfer-TransparentContainer,
        S1ap-ENB-UE-S1AP-ID,
        S1ap-ExtendedRepetitionPeriod,
        S1ap-GTP-TEID,
        S1ap-GUMMEI,
        S1ap-HandoverRestrictionList,
        S1ap-HandoverType,
        S1ap-LAI,
        S1ap-LPPa-PDU,
        S1ap-ManagementBasedMDTAllowed,
        S1ap-MMEname,
        S1ap-MMERelaySupportIndicator,
        S1ap-MME-UE-S1AP-ID,
        S1ap-MSClassmark2,
        S1ap-MSClassmark3,
        S1ap-NAS-PDU,
        S1ap-NASSecurityParametersfromE-UTRAN,
        S1ap-NASSecurityParameterstoE-UTRAN,
        S1ap-OverloadResponse,
        S1ap-PagingDRX,
        S1ap-PagingPriority,
        S1ap-PLMNidentity,
        S1ap-RIMTransfer,
        S1ap-RelativeMMECapacity,
        S1ap-RequestType,
        S1ap-E-RAB-ID,
        S1ap-E-RABLevelQoSParameters,
        S1ap-E-RABList,
        S1ap-RelayNode-Indicator,
        S1ap-Routing-ID,
        S1ap-SecurityKey,
        S1ap-SecurityContext,
        S1ap-ServedGUMMEIs,
        S1ap-SONConfigurationTransfer,
        S1ap-Source-ToTarget-TransparentContainer,
        S1ap-SourceBSS-ToTargetBSS-TransparentContainer,
        S1ap-SourceeNB-ToTargeteNB-TransparentContainer,
        S1ap-SourceRNC-ToTargetRNC-TransparentContainer,
        S1ap-SubscriberProfileIDforRFP,
        S1ap-SRVCCOperationPossible,
        S1ap-SRVCCHOIndication,
        S1ap-SupportedTAs,
        S1ap-TAI,
        S1ap-Target-ToSource-TransparentContainer,
        S1ap-TargetBSS-ToSourceBSS-TransparentContainer,        
        S1ap-TargeteNB-ToSourceeNB-TransparentContainer,
        S1ap-TargetID,
        S1ap-TargetRNC-ToSourceRNC-TransparentContainer,
        S1ap-TimeToWait,
        S1ap-TraceActivation,
        S1ap-TrafficLoadReductionIndication,
        S1ap-E-UTRAN-Trace-ID,
        S1ap-TransportLayerAddress,
        S1ap-UEIdentityIndexValue,
        S1ap-UEPagingID,
        S1ap-UERadioCapability,
        S1ap-UE-S1AP-IDs,
        S1ap-UE-associatedLogicalS1-ConnectionItem,
        S1ap-UESecurityCapabilities,
        S1ap-S-TMSI,
        S1ap-MessageIdentifier,
        S1ap-SerialNumber,
        S1ap-WarningAreaList,
        S1ap-RepetitionPeriod,
        S1ap-NumberofBroadcastRequest,
        S1ap-WarningType,
        S1ap-WarningSecurityInfo,
        S1ap-DataCodingScheme,
        S1ap-WarningMessageContents,
        S1ap-BroadcastCompletedAreaList,
        S1ap-RRC-Establishment-Cause,
        S1ap-BroadcastCancelledAreaList,
        S1ap-PS-ServiceNotAvailable,
        S1ap-GUMMEIList,
        S1ap-Correlation-ID,
        S1ap-GWContextReleaseIndication,
        S1ap-PrivacyIndicator






FROM S1AP-IEs


        PrivateIE-Container{},
        ProtocolExtensionContainer{},
        ProtocolIE-Container{},
        ProtocolIE-ContainerList{},
        ProtocolIE-ContainerPair{},
        ProtocolIE-ContainerPairList{},
        ProtocolIE-SingleContainer{},
        S1AP-PRIVATE-IES,
        S1AP-PROTOCOL-EXTENSION,
        S1AP-PROTOCOL-IES,
        S1AP-PROTOCOL-IES-PAIR
FROM S1AP-Containers




        id-uEaggregateMaximumBitrate,
        id-Cause,
        id-CellAccessMode,
        id-cdma2000HORequiredIndication,
        id-cdma2000HOStatus,
        id-cdma2000OneXSRVCCInfo,
        id-cdma2000OneXRAND,
        id-cdma2000PDU,
        id-cdma2000RATType,
        id-cdma2000SectorID,
        id-EUTRANRoundTripDelayEstimationInfo,
        id-CNDomain,
        id-ConcurrentWarningMessageIndicator,
        id-CriticalityDiagnostics,
        id-CSFallbackIndicator,
        id-CSG-Id,
        id-CSG-IdList, 
        id-CSGMembershipStatus, 
        id-Data-Forwarding-Not-Possible,
        id-DefaultPagingDRX,
        id-Direct-Forwarding-Path-Availability,
        id-Global-ENB-ID,
        id-EUTRAN-CGI,
        id-eNBname,
        id-eNB-StatusTransfer-TransparentContainer,
        id-eNB-UE-S1AP-ID, 
        id-GERANtoLTEHOInformationRes,
        id-GUMMEI-ID,
        id-HandoverRestrictionList,
        id-HandoverType,
        id-InitialContextSetup,
        id-Inter-SystemInformationTransferTypeEDT,
        id-Inter-SystemInformationTransferTypeMDT,
        id-LPPa-PDU,
        id-NAS-DownlinkCount,
        id-ManagementBasedMDTAllowed,
        id-MMEname,
        id-MME-UE-S1AP-ID,
        id-MSClassmark2,
        id-MSClassmark3,
        id-NAS-PDU,
        id-NASSecurityParametersfromE-UTRAN,
        id-NASSecurityParameterstoE-UTRAN,
        id-OverloadResponse,
        id-pagingDRX,
        id-PagingPriority,
        id-RelativeMMECapacity,
        id-RequestType,
        id-Routing-ID,
        id-E-RABAdmittedItem,
        id-E-RABAdmittedList,
        id-E-RABDataForwardingItem,
        id-E-RABFailedToModifyList,
        id-E-RABFailedToReleaseList,
        id-E-RABFailedtoSetupItemHOReqAck,
        id-E-RABFailedToSetupListBearerSURes,
        id-E-RABFailedToSetupListCtxtSURes,
        id-E-RABFailedToSetupListHOReqAck,
        id-E-RABFailedToBeReleasedList,
        id-E-RABModify,
        id-E-RABModifyItemBearerModRes,
        id-E-RABModifyListBearerModRes,
        id-E-RABRelease,
        id-E-RABReleaseItemBearerRelComp,
        id-E-RABReleaseItemHOCmd,
        id-E-RABReleaseListBearerRelComp,
        id-E-RABReleaseIndication,
        id-E-RABSetup,
        id-E-RABSetupItemBearerSURes,
        id-E-RABSetupItemCtxtSURes,
        id-E-RABSetupListBearerSURes,
        id-E-RABSetupListCtxtSURes,
        id-E-RABDataForwardingList,
        id-E-RABToBeModifiedItemBearerModReq,
        id-E-RABToBeModifiedListBearerModReq,
        id-E-RABToBeReleasedList,
        id-E-RABReleasedList,
        id-E-RABToBeSetupItemBearerSUReq,
        id-E-RABToBeSetupItemCtxtSUReq,
        id-E-RABToBeSetupItemHOReq,
        id-E-RABToBeSetupListBearerSUReq,
        id-E-RABToBeSetupListCtxtSUReq,
        id-E-RABToBeSetupListHOReq,
        id-E-RABToBeSwitchedDLItem,
        id-E-RABToBeSwitchedDLList,
        id-E-RABToBeSwitchedULList,
        id-E-RABToBeSwitchedULItem,
        id-E-RABtoReleaseListHOCmd,
        id-SecurityKey,
        id-SecurityContext,
        id-ServedGUMMEIs,
        id-SONConfigurationTransferECT,
        id-SONConfigurationTransferMCT,
        id-Source-ToTarget-TransparentContainer,
        id-Source-ToTarget-TransparentContainer-Secondary,
        id-SourceMME-UE-S1AP-ID,
        id-SRVCCOperationPossible,
        id-SRVCCHOIndication,
        id-SubscriberProfileIDforRFP,
        id-SupportedTAs,
        id-S-TMSI,
        id-TAI,
        id-TAIItem,
        id-TAIList,
        id-Target-ToSource-TransparentContainer,
        id-Target-ToSource-TransparentContainer-Secondary,
        id-TargetID,
        id-TimeToWait,
        id-TraceActivation,
        id-TrafficLoadReductionIndication,
        id-E-UTRAN-Trace-ID,
        id-UEIdentityIndexValue,
        id-UEPagingID,
        id-UERadioCapability,
        id-UTRANtoLTEHOInformationRes,
        id-UE-associatedLogicalS1-ConnectionListResAck,
        id-UE-associatedLogicalS1-ConnectionItem,
        id-UESecurityCapabilities,
        id-UE-S1AP-IDs,
        id-ResetType,
        id-MessageIdentifier,
        id-SerialNumber,
        id-WarningAreaList,
        id-RepetitionPeriod,
        id-NumberofBroadcastRequest,
        id-WarningType,
        id-WarningSecurityInfo,
        id-DataCodingScheme,
        id-WarningMessageContents,
        id-BroadcastCompletedAreaList,
        id-BroadcastCancelledAreaList,
        id-RRC-Establishment-Cause,
        id-TraceCollectionEntityIPAddress,
        s1ap-maxnoofTAIs,
        s1ap-maxNrOfErrors,
        s1ap-maxNrOfE-RABs,
        s1ap-maxNrOfIndividualS1ConnectionsToReset,
        s1ap-maxnoofEmergencyAreaID,
        s1ap-maxnoofCellID,
        s1ap-maxnoofTAIforWarning,
        s1ap-maxnoofCellinTAI,
        s1ap-maxnoofCellinEAI,
        id-ExtendedRepetitionPeriod,
        id-PS-ServiceNotAvailable,
        id-RegisteredLAI,
        id-GUMMEIList,
        id-SourceMME-GUMMEI,
        id-MME-UE-S1AP-ID-2,
        id-GW-TransportLayerAddress,
        id-RelayNode-Indicator,
        id-Correlation-ID,
        id-MMERelaySupportIndicator,
        id-GWContextReleaseIndication,
        id-PrivacyIndicator,
        s1ap-maxProtocolIEs

FROM S1AP-Constants

        S1ap-IE

FROM S1AP-PDU;


-- **************************************************************
--
-- Common Container Lists
--
-- **************************************************************


E-RAB-IE-ContainerList                        { S1AP-PROTOCOL-IES      : IEsSetParam }        ::= ProtocolIE-ContainerList     { 1, s1ap-maxNrOfE-RABs,   {IEsSetParam} }
E-RAB-IE-ContainerPairList                { S1AP-PROTOCOL-IES-PAIR : IEsSetParam }        ::= ProtocolIE-ContainerPairList { 1, s1ap-maxNrOfE-RABs,   {IEsSetParam} }
ProtocolError-IE-ContainerList        { S1AP-PROTOCOL-IES      : IEsSetParam }        ::= ProtocolIE-ContainerList     { 1, s1ap-maxNrOfE-RABs,   {IEsSetParam} }


-- **************************************************************
--
-- HANDOVER PREPARATION ELEMENTARY PROCEDURE
--
-- **************************************************************


-- **************************************************************
--
-- Handover Required
--
-- **************************************************************


S1ap-HandoverRequired ::= SEQUENCE {
    s1ap-HandoverRequired-ies SEQUENCE (SIZE (0..s1ap-maxProtocolIEs)) OF S1ap-IE,
        ...
}


S1ap-HandoverRequiredIEs S1AP-PROTOCOL-IES ::= {        
        { ID id-MME-UE-S1AP-ID                                                        CRITICALITY reject        TYPE S1ap-MME-UE-S1AP-ID                                                                         PRESENCE mandatory }|
        { ID id-eNB-UE-S1AP-ID                                                        CRITICALITY reject        TYPE S1ap-ENB-UE-S1AP-ID                                                                         PRESENCE mandatory }|
        { ID id-HandoverType                                                        CRITICALITY reject        TYPE S1ap-HandoverType                                                                         PRESENCE mandatory }|
        { ID id-Cause                                                                        CRITICALITY ignore        TYPE S1ap-Cause                                                                                         PRESENCE mandatory }|
        { ID id-TargetID                                                                CRITICALITY reject        TYPE S1ap-TargetID                                                                                 PRESENCE mandatory }|
        { ID id-Direct-Forwarding-Path-Availability                CRITICALITY ignore        TYPE S1ap-Direct-Forwarding-Path-Availability                PRESENCE optional }|
        { ID id-SRVCCHOIndication                                                CRITICALITY reject        TYPE S1ap-SRVCCHOIndication                                                                PRESENCE optional }|
        { ID id-Source-ToTarget-TransparentContainer        CRITICALITY reject        TYPE S1ap-Source-ToTarget-TransparentContainer         PRESENCE mandatory }|
        { ID id-Source-ToTarget-TransparentContainer-Secondary         CRITICALITY reject         TYPE S1ap-Source-ToTarget-TransparentContainer        PRESENCE optional }|
        { ID id-MSClassmark2                                                        CRITICALITY reject        TYPE S1ap-MSClassmark2                                                                        PRESENCE conditional }|
        { ID id-MSClassmark3                                                        CRITICALITY ignore        TYPE S1ap-MSClassmark3                                                                        PRESENCE conditional }|
        { ID id-CSG-Id                                                                        CRITICALITY reject        TYPE S1ap-CSG-Id                                                                                        PRESENCE optional }|
        { ID id-CellAccessMode                                                        CRITICALITY reject        TYPE S1ap-CellAccessMode                                                                        PRESENCE optional }|
        { ID id-PS-ServiceNotAvailable                                        CRITICALITY ignore        TYPE S1ap-PS-ServiceNotAvailable                                                PRESENCE optional },
        ...
}




-- **************************************************************
--
-- Handover Command
--
-- **************************************************************


S1ap-HandoverCommand ::= SEQUENCE {
    s1ap-HandoverCommand-ies SEQUENCE (SIZE (0..s1ap-maxProtocolIEs)) OF S1ap-IE,
        ...
}


S1ap-HandoverCommandIEs S1AP-PROTOCOL-IES ::= {        
        { ID id-MME-UE-S1AP-ID                                                        CRITICALITY reject        TYPE S1ap-MME-UE-S1AP-ID                                                                                         PRESENCE mandatory        } |
        { ID id-eNB-UE-S1AP-ID                                                        CRITICALITY reject        TYPE S1ap-ENB-UE-S1AP-ID                                                                                         PRESENCE mandatory        } |
        { ID id-HandoverType                                                        CRITICALITY reject        TYPE S1ap-HandoverType                                                                                         PRESENCE mandatory        } |
        { ID id-NASSecurityParametersfromE-UTRAN                CRITICALITY reject        TYPE S1ap-NASSecurityParametersfromE-UTRAN                                        PRESENCE conditional
        -- This IE shall be present if S1ap-HandoverType IE is set to value "LTEtoUTRAN" or "LTEtoGERAN" --                        }|
        { ID id-E-RABDataForwardingList                CRITICALITY ignore        TYPE S1ap-E-RABDataForwardingList                                         PRESENCE optional        } |
        { ID id-E-RABtoReleaseListHOCmd                                        CRITICALITY ignore        TYPE S1ap-E-RABList                                                                                                 PRESENCE optional        } |
        { ID id-Target-ToSource-TransparentContainer        CRITICALITY        reject        TYPE S1ap-Target-ToSource-TransparentContainer                        PRESENCE mandatory }|
        { ID id-Target-ToSource-TransparentContainer-Secondary        CRITICALITY        reject        TYPE S1ap-Target-ToSource-TransparentContainer                        PRESENCE optional }|
        { ID id-CriticalityDiagnostics                                        CRITICALITY ignore        TYPE S1ap-CriticalityDiagnostics                                                                PRESENCE optional        },
        ...
}


S1ap-E-RABDataForwardingList ::= E-RAB-IE-ContainerList { {S1ap-E-RABDataForwardingItemIEs} }


S1ap-E-RABDataForwardingItemIEs S1AP-PROTOCOL-IES ::= {
        { ID id-E-RABDataForwardingItem                        CRITICALITY ignore        TYPE S1ap-E-RABDataForwardingItem                        PRESENCE mandatory        },
        ...
}


S1ap-E-RABDataForwardingItem ::= SEQUENCE {
        e-RAB-ID                                                        S1ap-E-RAB-ID,
        dL-transportLayerAddress                        S1ap-TransportLayerAddress                                                                                                         OPTIONAL,
        dL-gTP-TEID                                                        S1ap-GTP-TEID                                                                                                                                 OPTIONAL,
        uL-S1ap-TransportLayerAddress                        S1ap-TransportLayerAddress                                                                                                        OPTIONAL,
        uL-S1ap-GTP-TEID                                                        S1ap-GTP-TEID                                                                                                                                OPTIONAL,
        iE-Extensions                                                ProtocolExtensionContainer { { S1ap-E-RABDataForwardingItem-ExtIEs} }        OPTIONAL,
        ...
}


S1ap-E-RABDataForwardingItem-ExtIEs S1AP-PROTOCOL-EXTENSION ::= {
        ...
}






-- **************************************************************
--
-- Handover Preparation Failure
--
-- **************************************************************


S1ap-HandoverPreparationFailure ::= SEQUENCE {
    s1ap-HandoverPreparationFailure-ies SEQUENCE (SIZE (0..s1ap-maxProtocolIEs)) OF S1ap-IE,
        ...
}


S1ap-HandoverPreparationFailureIEs S1AP-PROTOCOL-IES ::= {        
        { ID id-MME-UE-S1AP-ID                                        CRITICALITY ignore        TYPE S1ap-MME-UE-S1AP-ID                                         PRESENCE mandatory        } |
        { ID id-eNB-UE-S1AP-ID                                        CRITICALITY ignore        TYPE S1ap-ENB-UE-S1AP-ID                                         PRESENCE mandatory        } |
        { ID id-Cause                                                        CRITICALITY ignore        TYPE S1ap-Cause                                                         PRESENCE mandatory        }|
        { ID id-CriticalityDiagnostics                        CRITICALITY ignore        TYPE S1ap-CriticalityDiagnostics                        PRESENCE optional        },
        ...
}


-- **************************************************************
--
-- HANDOVER RESOURCE ALLOCATION ELEMENTARY PROCEDURE
--
-- **************************************************************


-- **************************************************************
--
-- Handover Request
--
-- **************************************************************


S1ap-HandoverRequest ::= SEQUENCE {
    s1ap-HandoverRequest-ies SEQUENCE (SIZE (0..s1ap-maxProtocolIEs)) OF S1ap-IE,
        ...
}


S1ap-HandoverRequestIEs S1AP-PROTOCOL-IES ::= {        
        { ID id-MME-UE-S1AP-ID                                                        CRITICALITY reject        TYPE S1ap-MME-UE-S1AP-ID                                                PRESENCE mandatory}|
        { ID id-HandoverType                                                        CRITICALITY reject        TYPE S1ap-HandoverType                                                PRESENCE mandatory}|
        { ID id-Cause                                                                        CRITICALITY ignore        TYPE S1ap-Cause                                                                 PRESENCE mandatory}|
        { ID id-uEaggregateMaximumBitrate                                CRITICALITY reject        TYPE S1ap-UEAggregateMaximumBitrate                        PRESENCE mandatory}|
        { ID id-E-RABToBeSetupListHOReq                                        CRITICALITY reject        TYPE S1ap-E-RABToBeSetupListHOReq                        PRESENCE mandatory}|
        { ID id-Source-ToTarget-TransparentContainer        CRITICALITY reject        TYPE S1ap-Source-ToTarget-TransparentContainer        PRESENCE mandatory}|
        { ID id-UESecurityCapabilities                                        CRITICALITY reject        TYPE S1ap-UESecurityCapabilities                        PRESENCE mandatory}|
        { ID id-HandoverRestrictionList                                        CRITICALITY ignore        TYPE S1ap-HandoverRestrictionList                        PRESENCE optional}|
        { ID id-TraceActivation                                                        CRITICALITY ignore        TYPE S1ap-TraceActivation                                        PRESENCE optional}|
        { ID id-RequestType                                                                CRITICALITY ignore        TYPE S1ap-RequestType                                                PRESENCE optional}|
        { ID id-SRVCCOperationPossible                                        CRITICALITY ignore        TYPE S1ap-SRVCCOperationPossible                        PRESENCE optional}|
        { ID id-SecurityContext                                                        CRITICALITY reject        TYPE S1ap-SecurityContext                                        PRESENCE mandatory}|
        { ID id-NASSecurityParameterstoE-UTRAN                        CRITICALITY reject        TYPE S1ap-NASSecurityParameterstoE-UTRAN                PRESENCE conditional
        -- This IE shall be present if the Handover Type IE is set to the value "UTRANtoLTE" or "GERANtoLTE" --}|
        { ID id-CSG-Id                                                                        CRITICALITY reject        TYPE S1ap-CSG-Id                                                                PRESENCE optional}|
        { ID id-CSGMembershipStatus                                                CRITICALITY ignore        TYPE S1ap-CSGMembershipStatus                                PRESENCE optional}|
        { ID id-GUMMEI-ID                                                                CRITICALITY ignore        TYPE S1ap-GUMMEI                                                                PRESENCE optional}|
        { ID id-MME-UE-S1AP-ID-2                                                CRITICALITY ignore        TYPE S1ap-MME-UE-S1AP-ID                                                PRESENCE optional}|
        { ID id-ManagementBasedMDTAllowed                                CRITICALITY ignore        TYPE S1ap-ManagementBasedMDTAllowed                        PRESENCE optional},
        ...
}


S1ap-E-RABToBeSetupListHOReq                                         ::= E-RAB-IE-ContainerList { {S1ap-E-RABToBeSetupItemHOReqIEs} }


S1ap-E-RABToBeSetupItemHOReqIEs S1AP-PROTOCOL-IES ::= {
        { ID id-E-RABToBeSetupItemHOReq                        CRITICALITY reject        TYPE S1ap-E-RABToBeSetupItemHOReq                        PRESENCE mandatory        },
        ...
}


S1ap-E-RABToBeSetupItemHOReq ::= SEQUENCE {
        e-RAB-ID                                                        S1ap-E-RAB-ID,
        transportLayerAddress                                S1ap-TransportLayerAddress,
        gTP-TEID                                                        S1ap-GTP-TEID,
        e-RABlevelQosParameters                                S1ap-E-RABLevelQoSParameters,
        iE-Extensions                                                ProtocolExtensionContainer { {S1ap-E-RABToBeSetupItemHOReq-ExtIEs} }                        OPTIONAL,
        ...
}


S1ap-E-RABToBeSetupItemHOReq-ExtIEs S1AP-PROTOCOL-EXTENSION ::= {
        {ID        id-Data-Forwarding-Not-Possible           CRITICALITY ignore        EXTENSION  S1ap-Data-Forwarding-Not-Possible   PRESENCE optional},
        ...
}


-- **************************************************************
--
-- Handover Request Acknowledge
--
-- **************************************************************


S1ap-HandoverRequestAcknowledge ::= SEQUENCE {
    s1ap-HandoverRequestAcknowledge-ies SEQUENCE (SIZE (0..s1ap-maxProtocolIEs)) OF S1ap-IE,
        ...
}


S1ap-HandoverRequestAcknowledgeIEs S1AP-PROTOCOL-IES ::= {        
        { ID id-MME-UE-S1AP-ID                                                        CRITICALITY ignore        TYPE S1ap-MME-UE-S1AP-ID                                                                        PRESENCE mandatory        } |
        { ID id-eNB-UE-S1AP-ID                                                        CRITICALITY ignore        TYPE S1ap-ENB-UE-S1AP-ID                                                                        PRESENCE mandatory        } |
        { ID id-E-RABAdmittedList                                                CRITICALITY ignore        TYPE S1ap-E-RABAdmittedList                                                                PRESENCE mandatory        } |
        { ID id-E-RABFailedToSetupListHOReqAck                        CRITICALITY ignore        TYPE S1ap-E-RABFailedtoSetupListHOReqAck                        PRESENCE optional        } |
        { ID id-Target-ToSource-TransparentContainer        CRITICALITY reject        TYPE S1ap-Target-ToSource-TransparentContainer        PRESENCE mandatory }|
        { ID id-CSG-Id                                                                        CRITICALITY ignore        TYPE S1ap-CSG-Id                                                                                        PRESENCE optional } |
        { ID id-CriticalityDiagnostics                                        CRITICALITY ignore        TYPE S1ap-CriticalityDiagnostics                                                PRESENCE optional        },
        ...
}


S1ap-E-RABAdmittedList                                         ::= E-RAB-IE-ContainerList { {S1ap-E-RABAdmittedItemIEs} }


S1ap-E-RABAdmittedItemIEs S1AP-PROTOCOL-IES ::= {
        { ID id-E-RABAdmittedItem                        CRITICALITY ignore        TYPE S1ap-E-RABAdmittedItem                        PRESENCE mandatory        },
        ...
}


S1ap-E-RABAdmittedItem ::= SEQUENCE {
        e-RAB-ID                                                S1ap-E-RAB-ID,
        transportLayerAddress                        S1ap-TransportLayerAddress,
        gTP-TEID                                                S1ap-GTP-TEID,
        dL-transportLayerAddress                S1ap-TransportLayerAddress        OPTIONAL,
        dL-gTP-TEID                                                S1ap-GTP-TEID                                OPTIONAL,
        uL-S1ap-TransportLayerAddress                S1ap-TransportLayerAddress        OPTIONAL,
        uL-S1ap-GTP-TEID                                                S1ap-GTP-TEID                                OPTIONAL,
        iE-Extensions                                        ProtocolExtensionContainer { {S1ap-E-RABAdmittedItem-ExtIEs} }        OPTIONAL,
        ...
}


S1ap-E-RABAdmittedItem-ExtIEs S1AP-PROTOCOL-EXTENSION ::= {
        ...
}


S1ap-E-RABFailedtoSetupListHOReqAck                                         ::= E-RAB-IE-ContainerList { {S1ap-E-RABFailedtoSetupItemHOReqAckIEs} }


S1ap-E-RABFailedtoSetupItemHOReqAckIEs S1AP-PROTOCOL-IES ::= {
        { ID id-E-RABFailedtoSetupItemHOReqAck                        CRITICALITY ignore        TYPE S1ap-E-RABFailedToSetupItemHOReqAck                        PRESENCE mandatory        },
        ...
}


S1ap-E-RABFailedToSetupItemHOReqAck ::= SEQUENCE {
        e-RAB-ID                                                S1ap-E-RAB-ID,
        cause                                S1ap-Cause,
        iE-Extensions                                        ProtocolExtensionContainer { { S1ap-E-RABFailedToSetupItemHOReqAckExtIEs} }                        OPTIONAL,
        ...
}


S1ap-E-RABFailedToSetupItemHOReqAckExtIEs S1AP-PROTOCOL-EXTENSION ::= {
        ...
}




-- **************************************************************
--
-- Handover Failure
--
-- **************************************************************


S1ap-HandoverFailure ::= SEQUENCE {
    s1ap-HandoverFailure-ies SEQUENCE (SIZE (0..s1ap-maxProtocolIEs)) OF S1ap-IE,
        ...
}


S1ap-HandoverFailureIEs S1AP-PROTOCOL-IES ::= {        
        { ID id-MME-UE-S1AP-ID                                CRITICALITY ignore        TYPE S1ap-MME-UE-S1AP-ID                                PRESENCE mandatory        } |
        { ID id-Cause                                                CRITICALITY ignore        TYPE S1ap-Cause                                                 PRESENCE mandatory        }|
        { ID id-CriticalityDiagnostics                CRITICALITY ignore        TYPE S1ap-CriticalityDiagnostics                PRESENCE optional        },
        ...
}


-- **************************************************************
--
-- HANDOVER NOTIFICATION ELEMENTARY PROCEDURE
--
-- **************************************************************


-- **************************************************************
--
-- Handover Notify
--
-- **************************************************************


S1ap-HandoverNotify ::= SEQUENCE {
    s1ap-HandoverNotify-ies SEQUENCE (SIZE (0..s1ap-maxProtocolIEs)) OF S1ap-IE,
        ...
}


S1ap-HandoverNotifyIEs S1AP-PROTOCOL-IES ::= {        
        { ID id-MME-UE-S1AP-ID                        CRITICALITY reject        TYPE S1ap-MME-UE-S1AP-ID                        PRESENCE mandatory        } |
        { ID id-eNB-UE-S1AP-ID                        CRITICALITY reject        TYPE S1ap-ENB-UE-S1AP-ID                        PRESENCE mandatory        } |
        { ID id-EUTRAN-CGI                                CRITICALITY ignore        TYPE S1ap-EUTRAN-CGI                                PRESENCE mandatory}|
        { ID id-TAI                                                CRITICALITY ignore        TYPE S1ap-TAI                                        PRESENCE mandatory},
        ...
}


-- **************************************************************
--
-- PATH SWITCH REQUEST ELEMENTARY PROCEDURE
--
-- **************************************************************


-- **************************************************************
--
-- Path Switch Request
--
-- **************************************************************


S1ap-PathSwitchRequest ::= SEQUENCE {
    s1ap-PathSwitchRequest-ies SEQUENCE (SIZE (0..s1ap-maxProtocolIEs)) OF S1ap-IE,
        ...
}


S1ap-PathSwitchRequestIEs S1AP-PROTOCOL-IES ::= {        
        { ID id-eNB-UE-S1AP-ID                                        CRITICALITY reject        TYPE S1ap-ENB-UE-S1AP-ID                                 PRESENCE mandatory}|
        { ID id-E-RABToBeSwitchedDLList                        CRITICALITY reject        TYPE S1ap-E-RABToBeSwitchedDLList        PRESENCE mandatory}|
        { ID id-SourceMME-UE-S1AP-ID                        CRITICALITY reject        TYPE S1ap-MME-UE-S1AP-ID                                 PRESENCE mandatory}|
        { ID id-EUTRAN-CGI                                                CRITICALITY ignore        TYPE S1ap-EUTRAN-CGI                                        PRESENCE mandatory}|
        { ID id-TAI                                                                CRITICALITY ignore        TYPE S1ap-TAI                                                PRESENCE mandatory}|
        { ID id-UESecurityCapabilities                        CRITICALITY ignore        TYPE S1ap-UESecurityCapabilities                PRESENCE mandatory}|
        { ID id-CSG-Id                                                        CRITICALITY ignore        TYPE S1ap-CSG-Id                                                PRESENCE optional}|
        { ID id-CellAccessMode                                        CRITICALITY ignore        TYPE S1ap-CellAccessMode                                PRESENCE optional}|
        { ID id-SourceMME-GUMMEI                                CRITICALITY ignore        TYPE S1ap-GUMMEI                                                PRESENCE optional},
        ...
}


S1ap-E-RABToBeSwitchedDLList                                         ::= E-RAB-IE-ContainerList { {S1ap-E-RABToBeSwitchedDLItemIEs} }


S1ap-E-RABToBeSwitchedDLItemIEs S1AP-PROTOCOL-IES ::= {
        { ID id-E-RABToBeSwitchedDLItem                        CRITICALITY reject        TYPE S1ap-E-RABToBeSwitchedDLItem                        PRESENCE mandatory        },
        ...
}


S1ap-E-RABToBeSwitchedDLItem ::= SEQUENCE {
        e-RAB-ID                                                S1ap-E-RAB-ID,
        transportLayerAddress                                S1ap-TransportLayerAddress,
        gTP-TEID                                        S1ap-GTP-TEID,
        iE-Extensions                                        ProtocolExtensionContainer { { S1ap-E-RABToBeSwitchedDLItem-ExtIEs} }                        OPTIONAL,
        ...
}


S1ap-E-RABToBeSwitchedDLItem-ExtIEs S1AP-PROTOCOL-EXTENSION ::= {
        ...
}


-- **************************************************************
--
-- Path Switch Request Acknowledge
--
-- **************************************************************


S1ap-PathSwitchRequestAcknowledge ::= SEQUENCE {
    s1ap-PathSwitchRequestAcknowledge-ies SEQUENCE (SIZE (0..s1ap-maxProtocolIEs)) OF S1ap-IE,
        ...
}


S1ap-PathSwitchRequestAcknowledgeIEs S1AP-PROTOCOL-IES ::= {        
        { ID id-MME-UE-S1AP-ID                                        CRITICALITY ignore        TYPE S1ap-MME-UE-S1AP-ID                                        PRESENCE mandatory}|
        { ID id-eNB-UE-S1AP-ID                                        CRITICALITY ignore        TYPE S1ap-ENB-UE-S1AP-ID                                        PRESENCE mandatory}|
        { ID id-uEaggregateMaximumBitrate                CRITICALITY ignore        TYPE S1ap-UEAggregateMaximumBitrate                PRESENCE optional}|
        { ID id-E-RABToBeSwitchedULList                        CRITICALITY ignore        TYPE S1ap-E-RABToBeSwitchedULList                PRESENCE optional}|
        { ID id-E-RABToBeReleasedList                        CRITICALITY ignore        TYPE S1ap-E-RABList                                                PRESENCE optional}|
        { ID id-SecurityContext                                        CRITICALITY reject        TYPE S1ap-SecurityContext                                PRESENCE mandatory}|
        { ID id-CriticalityDiagnostics                        CRITICALITY ignore        TYPE S1ap-CriticalityDiagnostics                        PRESENCE optional}|
        { ID id-MME-UE-S1AP-ID-2                                CRITICALITY ignore        TYPE S1ap-MME-UE-S1AP-ID                                        PRESENCE optional},
        ...
}


S1ap-E-RABToBeSwitchedULList ::= E-RAB-IE-ContainerList { {S1ap-E-RABToBeSwitchedULItemIEs} }


S1ap-E-RABToBeSwitchedULItemIEs S1AP-PROTOCOL-IES ::= {
        { ID id-E-RABToBeSwitchedULItem                CRITICALITY ignore        TYPE S1ap-E-RABToBeSwitchedULItem        PRESENCE mandatory        },
        ...
}


S1ap-E-RABToBeSwitchedULItem ::= SEQUENCE {
        e-RAB-ID                                                        S1ap-E-RAB-ID,
        transportLayerAddress                                S1ap-TransportLayerAddress,
        gTP-TEID                                                        S1ap-GTP-TEID,
        iE-Extensions                                                ProtocolExtensionContainer { { S1ap-E-RABToBeSwitchedULItem-ExtIEs} }                        OPTIONAL,
        ...
}


S1ap-E-RABToBeSwitchedULItem-ExtIEs S1AP-PROTOCOL-EXTENSION ::= {
        ...
}




-- **************************************************************
--
-- Path Switch Request Failure
--
-- **************************************************************


S1ap-PathSwitchRequestFailure ::= SEQUENCE {
    s1ap-PathSwitchRequestFailure-ies SEQUENCE (SIZE (0..s1ap-maxProtocolIEs)) OF S1ap-IE,
        ...
}


S1ap-PathSwitchRequestFailureIEs S1AP-PROTOCOL-IES ::= {        
        { ID id-MME-UE-S1AP-ID                                        CRITICALITY ignore        TYPE S1ap-MME-UE-S1AP-ID                                         PRESENCE mandatory        } |
        { ID id-eNB-UE-S1AP-ID                                        CRITICALITY ignore        TYPE S1ap-ENB-UE-S1AP-ID                                         PRESENCE mandatory        } |
        { ID id-Cause                                                        CRITICALITY ignore        TYPE S1ap-Cause                                                         PRESENCE mandatory        }|
        { ID id-CriticalityDiagnostics                        CRITICALITY ignore        TYPE S1ap-CriticalityDiagnostics                        PRESENCE optional        },
        ...
}


-- **************************************************************
--
-- HANDOVER CANCEL ELEMENTARY PROCEDURE
--
-- **************************************************************


-- **************************************************************
--
-- Handover Cancel
--
-- **************************************************************


S1ap-HandoverCancel ::= SEQUENCE {
    s1ap-HandoverCancel-ies SEQUENCE (SIZE (0..s1ap-maxProtocolIEs)) OF S1ap-IE,
        ...
}


S1ap-HandoverCancelIEs S1AP-PROTOCOL-IES ::= {        
        { ID id-MME-UE-S1AP-ID                                        CRITICALITY reject        TYPE S1ap-MME-UE-S1AP-ID                                         PRESENCE mandatory        } |
        { ID id-eNB-UE-S1AP-ID                                        CRITICALITY reject        TYPE S1ap-ENB-UE-S1AP-ID                                         PRESENCE mandatory        } |
        { ID id-Cause                                        CRITICALITY ignore        TYPE S1ap-Cause                                         PRESENCE mandatory        },
        ...
}


-- **************************************************************
--
-- Handover Cancel Request Acknowledge
--
-- **************************************************************


S1ap-HandoverCancelAcknowledge ::= SEQUENCE {
    s1ap-HandoverCancelAcknowledge-ies SEQUENCE (SIZE (0..s1ap-maxProtocolIEs)) OF S1ap-IE,
        ...
}


S1ap-HandoverCancelAcknowledgeIEs S1AP-PROTOCOL-IES ::= {        
        { ID id-MME-UE-S1AP-ID                                        CRITICALITY ignore        TYPE S1ap-MME-UE-S1AP-ID                                         PRESENCE mandatory        } |
        { ID id-eNB-UE-S1AP-ID                                        CRITICALITY ignore        TYPE S1ap-ENB-UE-S1AP-ID                                         PRESENCE mandatory        }|
        { ID id-CriticalityDiagnostics                CRITICALITY ignore        TYPE S1ap-CriticalityDiagnostics                        PRESENCE optional        },
        ...
}


-- **************************************************************
--
-- E-RAB SETUP ELEMENTARY PROCEDURE
--
-- **************************************************************


-- **************************************************************
--
-- E-RAB Setup Request
--
-- **************************************************************


S1ap-E-RABSetupRequest ::= SEQUENCE {
    s1ap-E-RABSetupRequest-ies SEQUENCE (SIZE (0..s1ap-maxProtocolIEs)) OF S1ap-IE,
        ...
}


S1ap-E-RABSetupRequestIEs S1AP-PROTOCOL-IES ::= {
        { ID id-MME-UE-S1AP-ID                                        CRITICALITY reject        TYPE S1ap-MME-UE-S1AP-ID                                                         PRESENCE mandatory        }|
        { ID id-eNB-UE-S1AP-ID                                        CRITICALITY reject        TYPE S1ap-ENB-UE-S1AP-ID                                                         PRESENCE mandatory        }|
        { ID id-uEaggregateMaximumBitrate                CRITICALITY reject        TYPE S1ap-UEAggregateMaximumBitrate                                PRESENCE optional        }|
        { ID id-E-RABToBeSetupListBearerSUReq        CRITICALITY reject        TYPE S1ap-E-RABToBeSetupListBearerSUReq                PRESENCE mandatory        },
        ...
}


S1ap-E-RABToBeSetupListBearerSUReq ::= SEQUENCE (SIZE(1.. s1ap-maxNrOfE-RABs)) OF ProtocolIE-SingleContainer { {S1ap-E-RABToBeSetupItemBearerSUReqIEs} }


S1ap-E-RABToBeSetupItemBearerSUReqIEs         S1AP-PROTOCOL-IES ::= {
        { ID id-E-RABToBeSetupItemBearerSUReq         CRITICALITY reject         TYPE S1ap-E-RABToBeSetupItemBearerSUReq         PRESENCE mandatory },
        ...
}


S1ap-E-RABToBeSetupItemBearerSUReq ::= SEQUENCE {
        e-RAB-ID                                                S1ap-E-RAB-ID,
        e-RABlevelQoSParameters                        S1ap-E-RABLevelQoSParameters,
        transportLayerAddress                         S1ap-TransportLayerAddress,
        gTP-TEID                                                S1ap-GTP-TEID,
        nAS-PDU                                                        S1ap-NAS-PDU,
        iE-Extensions                                        ProtocolExtensionContainer { {S1ap-E-RABToBeSetupItemBearerSUReqExtIEs} } OPTIONAL,
        ...
}




S1ap-E-RABToBeSetupItemBearerSUReqExtIEs S1AP-PROTOCOL-EXTENSION ::= {
        { ID id-Correlation-ID                CRITICALITY ignore        EXTENSION S1ap-Correlation-ID                PRESENCE optional},
        ...
}




-- **************************************************************
--
-- E-RAB Setup Response
--
-- **************************************************************


S1ap-E-RABSetupResponse ::= SEQUENCE {
    s1ap-E-RABSetupResponse-ies SEQUENCE (SIZE (0..s1ap-maxProtocolIEs)) OF S1ap-IE,
        ...
}


S1ap-E-RABSetupResponseIEs S1AP-PROTOCOL-IES ::= {
        { ID id-MME-UE-S1AP-ID                                CRITICALITY ignore        TYPE S1ap-MME-UE-S1AP-ID                                         PRESENCE mandatory        }|
        { ID id-eNB-UE-S1AP-ID                                CRITICALITY ignore        TYPE S1ap-ENB-UE-S1AP-ID                                         PRESENCE mandatory        }|
        { ID id-E-RABSetupListBearerSURes                                CRITICALITY ignore        TYPE S1ap-E-RABSetupListBearerSURes                        PRESENCE optional        }|
        { ID id-E-RABFailedToSetupListBearerSURes                CRITICALITY ignore        TYPE S1ap-E-RABList                                        PRESENCE optional        }|
        { ID id-CriticalityDiagnostics                CRITICALITY ignore        TYPE S1ap-CriticalityDiagnostics                        PRESENCE optional        },
        ...
}




S1ap-E-RABSetupListBearerSURes ::= SEQUENCE (SIZE(1.. s1ap-maxNrOfE-RABs)) OF ProtocolIE-SingleContainer { {S1ap-E-RABSetupItemBearerSUResIEs} }


S1ap-E-RABSetupItemBearerSUResIEs         S1AP-PROTOCOL-IES ::= {
        { ID id-E-RABSetupItemBearerSURes         CRITICALITY ignore         TYPE S1ap-E-RABSetupItemBearerSURes         PRESENCE mandatory },
        ...
}


S1ap-E-RABSetupItemBearerSURes ::= SEQUENCE {
        e-RAB-ID                                        S1ap-E-RAB-ID,
        transportLayerAddress                S1ap-TransportLayerAddress,
        gTP-TEID                                        S1ap-GTP-TEID,
        iE-Extensions                                ProtocolExtensionContainer { {S1ap-E-RABSetupItemBearerSUResExtIEs} } OPTIONAL,
        ...
}




S1ap-E-RABSetupItemBearerSUResExtIEs S1AP-PROTOCOL-EXTENSION ::= {
        ...
}






-- **************************************************************
--
-- E-RAB MODIFY ELEMENTARY PROCEDURE
--
-- **************************************************************


-- **************************************************************
--
-- E-RAB Modify Request
--
-- **************************************************************


S1ap-E-RABModifyRequest ::= SEQUENCE {
    s1ap-E-RABModifyRequest-ies SEQUENCE (SIZE (0..s1ap-maxProtocolIEs)) OF S1ap-IE,
        ...
}


S1ap-E-RABModifyRequestIEs S1AP-PROTOCOL-IES ::= {
        { ID id-MME-UE-S1AP-ID                                                CRITICALITY reject        TYPE S1ap-MME-UE-S1AP-ID                                                                PRESENCE mandatory        }|
        { ID id-eNB-UE-S1AP-ID                                                CRITICALITY reject        TYPE S1ap-ENB-UE-S1AP-ID                                                                PRESENCE mandatory        }|
        { ID id-uEaggregateMaximumBitrate                        CRITICALITY reject        TYPE S1ap-UEAggregateMaximumBitrate                                PRESENCE optional        }|
        { ID id-E-RABToBeModifiedListBearerModReq        CRITICALITY reject        TYPE S1ap-E-RABToBeModifiedListBearerModReq                PRESENCE mandatory        },
        ...
}


S1ap-E-RABToBeModifiedListBearerModReq ::= SEQUENCE (SIZE(1.. s1ap-maxNrOfE-RABs)) OF ProtocolIE-SingleContainer { {S1ap-E-RABToBeModifiedItemBearerModReqIEs} }


S1ap-E-RABToBeModifiedItemBearerModReqIEs         S1AP-PROTOCOL-IES ::= {
        { ID id-E-RABToBeModifiedItemBearerModReq         CRITICALITY reject         TYPE S1ap-E-RABToBeModifiedItemBearerModReq         PRESENCE mandatory },
        ...
}


S1ap-E-RABToBeModifiedItemBearerModReq ::= SEQUENCE {
        e-RAB-ID                                                S1ap-E-RAB-ID,
        e-RABLevelQoSParameters                        S1ap-E-RABLevelQoSParameters,
        nAS-PDU                                                        S1ap-NAS-PDU,
        iE-Extensions                                        ProtocolExtensionContainer { {S1ap-E-RABToBeModifyItemBearerModReqExtIEs} } OPTIONAL,
        ...
}




S1ap-E-RABToBeModifyItemBearerModReqExtIEs S1AP-PROTOCOL-EXTENSION ::= {
        ...
}






-- **************************************************************
--
-- E-RAB Modify Response
--
-- **************************************************************


S1ap-E-RABModifyResponse ::= SEQUENCE {
    s1ap-E-RABModifyResponse-ies SEQUENCE (SIZE (0..s1ap-maxProtocolIEs)) OF S1ap-IE,
        ...
}


S1ap-E-RABModifyResponseIEs S1AP-PROTOCOL-IES ::= {
        { ID id-MME-UE-S1AP-ID                                CRITICALITY ignore        TYPE S1ap-MME-UE-S1AP-ID                                         PRESENCE mandatory        }|
        { ID id-eNB-UE-S1AP-ID                                CRITICALITY ignore        TYPE S1ap-ENB-UE-S1AP-ID                                         PRESENCE mandatory        }|
        { ID id-E-RABModifyListBearerModRes                                CRITICALITY ignore        TYPE S1ap-E-RABModifyListBearerModRes                PRESENCE optional        }|
        { ID id-E-RABFailedToModifyList                CRITICALITY ignore        TYPE S1ap-E-RABList                                PRESENCE optional        }|
        { ID id-CriticalityDiagnostics                CRITICALITY ignore        TYPE S1ap-CriticalityDiagnostics                        PRESENCE optional        },
        ...
}




S1ap-E-RABModifyListBearerModRes ::= SEQUENCE (SIZE(1.. s1ap-maxNrOfE-RABs)) OF ProtocolIE-SingleContainer { {S1ap-E-RABModifyItemBearerModResIEs} }


S1ap-E-RABModifyItemBearerModResIEs         S1AP-PROTOCOL-IES ::= {
        { ID id-E-RABModifyItemBearerModRes         CRITICALITY ignore         TYPE S1ap-E-RABModifyItemBearerModRes         PRESENCE mandatory },
        ...
}


S1ap-E-RABModifyItemBearerModRes ::= SEQUENCE {
        e-RAB-ID                                        S1ap-E-RAB-ID,
        iE-Extensions                                        ProtocolExtensionContainer { {S1ap-E-RABModifyItemBearerModResExtIEs} } OPTIONAL,
        ...
}




S1ap-E-RABModifyItemBearerModResExtIEs S1AP-PROTOCOL-EXTENSION ::= {
        ...
}








-- **************************************************************
--
-- E-RAB RELEASE ELEMENTARY PROCEDURE
--
-- **************************************************************


-- **************************************************************
--
-- E-RAB Release Command
--
-- **************************************************************


S1ap-E-RABReleaseCommand ::= SEQUENCE {
    s1ap-E-RABReleaseCommand-ies SEQUENCE (SIZE (0..s1ap-maxProtocolIEs)) OF S1ap-IE,
        ...
}


S1ap-E-RABReleaseCommandIEs S1AP-PROTOCOL-IES ::= {
        { ID id-MME-UE-S1AP-ID                                CRITICALITY reject        TYPE S1ap-MME-UE-S1AP-ID                                         PRESENCE mandatory        }|
        { ID id-eNB-UE-S1AP-ID                                CRITICALITY reject        TYPE S1ap-ENB-UE-S1AP-ID                                         PRESENCE mandatory        }|
        { ID id-uEaggregateMaximumBitrate                CRITICALITY reject        TYPE S1ap-UEAggregateMaximumBitrate                PRESENCE optional        }|
        { ID id-E-RABToBeReleasedList                CRITICALITY ignore        TYPE S1ap-E-RABList                                        PRESENCE mandatory        }|
        { ID id-NAS-PDU                                                        CRITICALITY ignore        TYPE S1ap-NAS-PDU                                                PRESENCE optional        },
        ...
}




-- **************************************************************
--
-- E-RAB Release Response
--
-- **************************************************************


S1ap-E-RABReleaseResponse ::= SEQUENCE {
    s1ap-E-RABReleaseResponse-ies SEQUENCE (SIZE (0..s1ap-maxProtocolIEs)) OF S1ap-IE,
        ...
}


S1ap-E-RABReleaseResponseIEs S1AP-PROTOCOL-IES ::= {
        { ID id-MME-UE-S1AP-ID                                CRITICALITY ignore        TYPE S1ap-MME-UE-S1AP-ID                                         PRESENCE mandatory        }|
        { ID id-eNB-UE-S1AP-ID                                CRITICALITY ignore        TYPE S1ap-ENB-UE-S1AP-ID                                         PRESENCE mandatory        }|
        { ID id-E-RABReleaseListBearerRelComp                                CRITICALITY ignore        TYPE S1ap-E-RABReleaseListBearerRelComp                PRESENCE optional        }|
        { ID id-E-RABFailedToReleaseList                CRITICALITY ignore        TYPE S1ap-E-RABList                                PRESENCE optional        }|
        { ID id-CriticalityDiagnostics                CRITICALITY ignore        TYPE S1ap-CriticalityDiagnostics                        PRESENCE optional        },
        ...
}




S1ap-E-RABReleaseListBearerRelComp ::= SEQUENCE (SIZE(1.. s1ap-maxNrOfE-RABs)) OF ProtocolIE-SingleContainer { {S1ap-E-RABReleaseItemBearerRelCompIEs} }


S1ap-E-RABReleaseItemBearerRelCompIEs         S1AP-PROTOCOL-IES ::= {
        { ID id-E-RABReleaseItemBearerRelComp         CRITICALITY ignore         TYPE S1ap-E-RABReleaseItemBearerRelComp         PRESENCE mandatory },
        ...
}


S1ap-E-RABReleaseItemBearerRelComp ::= SEQUENCE {
        e-RAB-ID                                        S1ap-E-RAB-ID,
        iE-Extensions                                        ProtocolExtensionContainer { {S1ap-E-RABReleaseItemBearerRelCompExtIEs} } OPTIONAL,
        ...
}




S1ap-E-RABReleaseItemBearerRelCompExtIEs S1AP-PROTOCOL-EXTENSION ::= {
        ...
}






-- **************************************************************
--
-- E-RAB RELEASE INDICATION ELEMENTARY PROCEDURE
--
-- **************************************************************


-- **************************************************************
--
-- E-RAB Release Indication
--
-- **************************************************************


S1ap-E-RABReleaseIndication ::= SEQUENCE {
    s1ap-E-RABReleaseIndication-ies SEQUENCE (SIZE (0..s1ap-maxProtocolIEs)) OF S1ap-IE,
        ...
}


S1ap-E-RABReleaseIndicationIEs S1AP-PROTOCOL-IES ::= {
        { ID id-MME-UE-S1AP-ID                                CRITICALITY reject        TYPE S1ap-MME-UE-S1AP-ID                                         PRESENCE mandatory        }|
        { ID id-eNB-UE-S1AP-ID                                CRITICALITY reject        TYPE S1ap-ENB-UE-S1AP-ID                                         PRESENCE mandatory        }|
        { ID id-E-RABReleasedList                        CRITICALITY ignore        TYPE S1ap-E-RABList                                        PRESENCE mandatory        },
        ...
}
-- **************************************************************
--
-- INITIAL CONTEXT SETUP ELEMENTARY PROCEDURE
--
-- **************************************************************


-- **************************************************************
--
-- Initial Context Setup Request
--
-- **************************************************************


S1ap-InitialContextSetupRequest ::= SEQUENCE {
    s1ap-InitialContextSetupRequest-ies SEQUENCE (SIZE (0..s1ap-maxProtocolIEs)) OF S1ap-IE,
        ...
}


S1ap-InitialContextSetupRequestIEs S1AP-PROTOCOL-IES ::= {
        { ID id-MME-UE-S1AP-ID                                CRITICALITY reject        TYPE S1ap-MME-UE-S1AP-ID                                         PRESENCE mandatory}|
        { ID id-eNB-UE-S1AP-ID                                CRITICALITY reject        TYPE S1ap-ENB-UE-S1AP-ID                                         PRESENCE mandatory}|
        { ID id-uEaggregateMaximumBitrate        CRITICALITY reject        TYPE S1ap-UEAggregateMaximumBitrate                PRESENCE mandatory}|
        { ID id-E-RABToBeSetupListCtxtSUReq        CRITICALITY reject        TYPE S1ap-E-RABToBeSetupListCtxtSUReq        PRESENCE mandatory}|
        { ID id-UESecurityCapabilities                CRITICALITY reject        TYPE S1ap-UESecurityCapabilities                        PRESENCE mandatory}|
        { ID id-SecurityKey                                        CRITICALITY reject        TYPE S1ap-SecurityKey                                        PRESENCE mandatory}|
        { ID id-TraceActivation                                CRITICALITY ignore        TYPE S1ap-TraceActivation                                 PRESENCE optional}|
        { ID id-HandoverRestrictionList                CRITICALITY ignore        TYPE S1ap-HandoverRestrictionList                PRESENCE optional}|
        { ID id-UERadioCapability                        CRITICALITY ignore        TYPE S1ap-UERadioCapability                                PRESENCE optional}|
        { ID id-SubscriberProfileIDforRFP        CRITICALITY ignore        TYPE S1ap-SubscriberProfileIDforRFP                PRESENCE optional}|
        { ID id-CSFallbackIndicator                        CRITICALITY reject        TYPE S1ap-CSFallbackIndicator                        PRESENCE optional}|
        { ID id-SRVCCOperationPossible                CRITICALITY ignore        TYPE S1ap-SRVCCOperationPossible                        PRESENCE optional}|
        { ID id-CSGMembershipStatus                        CRITICALITY ignore        TYPE S1ap-CSGMembershipStatus                        PRESENCE optional}|
        { ID id-RegisteredLAI                                CRITICALITY ignore        TYPE S1ap-LAI                                                        PRESENCE optional}|
        { ID id-GUMMEI-ID                                        CRITICALITY ignore        TYPE S1ap-GUMMEI                                                        PRESENCE optional}|
        { ID id-MME-UE-S1AP-ID-2                        CRITICALITY ignore        TYPE S1ap-MME-UE-S1AP-ID                                        PRESENCE optional}|
        { ID id-ManagementBasedMDTAllowed        CRITICALITY ignore        TYPE S1ap-ManagementBasedMDTAllowed                PRESENCE optional},
        ...
}








S1ap-E-RABToBeSetupListCtxtSUReq ::= SEQUENCE (SIZE(1.. s1ap-maxNrOfE-RABs)) OF ProtocolIE-SingleContainer { {S1ap-E-RABToBeSetupItemCtxtSUReqIEs} }


S1ap-E-RABToBeSetupItemCtxtSUReqIEs         S1AP-PROTOCOL-IES ::= {
        { ID id-E-RABToBeSetupItemCtxtSUReq         CRITICALITY reject         TYPE S1ap-E-RABToBeSetupItemCtxtSUReq         PRESENCE mandatory },
        ...
}


S1ap-E-RABToBeSetupItemCtxtSUReq ::= SEQUENCE {
        e-RAB-ID                                        S1ap-E-RAB-ID,
        e-RABlevelQoSParameters                                        S1ap-E-RABLevelQoSParameters,                
        transportLayerAddress                         S1ap-TransportLayerAddress,
        gTP-TEID                        S1ap-GTP-TEID,
        nAS-PDU                                S1ap-NAS-PDU                OPTIONAL,
        iE-Extensions                                        ProtocolExtensionContainer { {S1ap-E-RABToBeSetupItemCtxtSUReqExtIEs} } OPTIONAL,
        ...
}




S1ap-E-RABToBeSetupItemCtxtSUReqExtIEs S1AP-PROTOCOL-EXTENSION ::= {
        { ID id-Correlation-ID                CRITICALITY ignore        EXTENSION S1ap-Correlation-ID                PRESENCE optional},
        ...
}




-- **************************************************************
--
-- Initial Context Setup Response
--
-- **************************************************************


S1ap-InitialContextSetupResponse ::= SEQUENCE {
    s1ap-InitialContextSetupResponse-ies SEQUENCE (SIZE (0..s1ap-maxProtocolIEs)) OF S1ap-IE,
        ...
}


S1ap-InitialContextSetupResponseIEs S1AP-PROTOCOL-IES ::= {
        { ID id-MME-UE-S1AP-ID                                                CRITICALITY ignore        TYPE S1ap-MME-UE-S1AP-ID                                         PRESENCE mandatory }|
        { ID id-eNB-UE-S1AP-ID                                                CRITICALITY ignore        TYPE S1ap-ENB-UE-S1AP-ID                                         PRESENCE mandatory }|
        { ID id-E-RABSetupListCtxtSURes                                CRITICALITY ignore        TYPE S1ap-E-RABSetupListCtxtSURes                PRESENCE mandatory }|
        { ID id-E-RABFailedToSetupListCtxtSURes                CRITICALITY ignore        TYPE S1ap-E-RABList                                                PRESENCE optional }|
        { ID id-CriticalityDiagnostics                                CRITICALITY ignore        TYPE S1ap-CriticalityDiagnostics                        PRESENCE optional },
        ...
}




S1ap-E-RABSetupListCtxtSURes ::= SEQUENCE (SIZE(1.. s1ap-maxNrOfE-RABs)) OF ProtocolIE-SingleContainer { {S1ap-E-RABSetupItemCtxtSUResIEs} }


S1ap-E-RABSetupItemCtxtSUResIEs         S1AP-PROTOCOL-IES ::= {
        { ID id-E-RABSetupItemCtxtSURes         CRITICALITY ignore         TYPE S1ap-E-RABSetupItemCtxtSURes         PRESENCE mandatory },
        ...
}


S1ap-E-RABSetupItemCtxtSURes ::= SEQUENCE {
        e-RAB-ID                                        S1ap-E-RAB-ID,
        transportLayerAddress                         S1ap-TransportLayerAddress,
        gTP-TEID                        S1ap-GTP-TEID,
        iE-Extensions                                        ProtocolExtensionContainer { {S1ap-E-RABSetupItemCtxtSUResExtIEs} } OPTIONAL,
        ...
}




S1ap-E-RABSetupItemCtxtSUResExtIEs S1AP-PROTOCOL-EXTENSION ::= {
        ...
}




-- **************************************************************
--
-- Initial Context Setup Failure
--
-- **************************************************************


S1ap-InitialContextSetupFailure ::= SEQUENCE {
    s1ap-InitialContextSetupFailure-ies SEQUENCE (SIZE (0..s1ap-maxProtocolIEs)) OF S1ap-IE,
        ...
}


S1ap-InitialContextSetupFailureIEs S1AP-PROTOCOL-IES ::= {
        { ID id-MME-UE-S1AP-ID                                CRITICALITY ignore        TYPE S1ap-MME-UE-S1AP-ID                                         PRESENCE mandatory }|
        { ID id-eNB-UE-S1AP-ID                                CRITICALITY ignore        TYPE S1ap-ENB-UE-S1AP-ID                                         PRESENCE mandatory }|
        { ID id-Cause                                                CRITICALITY ignore        TYPE S1ap-Cause                                                        PRESENCE mandatory }|
        { ID id-CriticalityDiagnostics                CRITICALITY ignore        TYPE S1ap-CriticalityDiagnostics                        PRESENCE optional },
        ...
}


-- **************************************************************
--
-- PAGING ELEMENTARY PROCEDURE
--
-- **************************************************************




-- **************************************************************
--
-- S1ap-Paging
--
-- **************************************************************


S1ap-Paging ::= SEQUENCE {
    s1ap-Paging-ies SEQUENCE (SIZE (0..s1ap-maxProtocolIEs)) OF S1ap-IE,
        ...
}


S1ap-PagingIEs S1AP-PROTOCOL-IES ::= {
        { ID id-UEIdentityIndexValue                CRITICALITY ignore        TYPE S1ap-UEIdentityIndexValue        PRESENCE mandatory}|
        { ID id-UEPagingID                                        CRITICALITY ignore        TYPE S1ap-UEPagingID                                PRESENCE mandatory}|
        { ID id-pagingDRX                                        CRITICALITY ignore        TYPE S1ap-PagingDRX                                PRESENCE optional}|
        { ID id-CNDomain                                        CRITICALITY ignore        TYPE S1ap-CNDomain                                PRESENCE mandatory}|
        { ID id-TAIList                                                CRITICALITY ignore        TYPE S1ap-TAIList                                PRESENCE mandatory}|
        { ID id-CSG-IdList                                        CRITICALITY ignore        TYPE S1ap-CSG-IdList                                PRESENCE optional}|
        { ID id-PagingPriority                                CRITICALITY ignore        TYPE S1ap-PagingPriority                        PRESENCE optional},
        ...
}


S1ap-TAIList::= SEQUENCE (SIZE(1.. s1ap-maxnoofTAIs)) OF ProtocolIE-SingleContainer {{S1ap-TAIItemIEs}}


S1ap-TAIItemIEs         S1AP-PROTOCOL-IES ::= {
        { ID id-TAIItem         CRITICALITY ignore                TYPE S1ap-TAIItem        PRESENCE mandatory },
        ...
}


S1ap-TAIItem ::= SEQUENCE {
        tAI                                                         S1ap-TAI,
        iE-Extensions                                        ProtocolExtensionContainer { {S1ap-TAIItemExtIEs} } OPTIONAL,
        ...
}




S1ap-TAIItemExtIEs S1AP-PROTOCOL-EXTENSION ::= {
        ...
}


-- **************************************************************
--
-- UE CONTEXT RELEASE ELEMENTARY PROCEDURE
--
-- **************************************************************


-- **************************************************************
--
-- UE CONTEXT RELEASE REQUEST
--
-- **************************************************************


S1ap-UEContextReleaseRequest ::= SEQUENCE {
    s1ap-UEContextReleaseRequest-ies SEQUENCE (SIZE (0..s1ap-maxProtocolIEs)) OF S1ap-IE,
        ...
}


S1ap-UEContextReleaseRequest-IEs S1AP-PROTOCOL-IES ::= {
        { ID id-MME-UE-S1AP-ID                                CRITICALITY reject        TYPE S1ap-MME-UE-S1AP-ID                                        PRESENCE mandatory}|
        { ID id-eNB-UE-S1AP-ID                                CRITICALITY reject        TYPE S1ap-ENB-UE-S1AP-ID                                        PRESENCE mandatory}|
        { ID id-Cause                                                CRITICALITY ignore        TYPE S1ap-Cause                                                        PRESENCE mandatory}|
        { ID id-GWContextReleaseIndication        CRITICALITY reject        TYPE S1ap-GWContextReleaseIndication                PRESENCE optional},
        ...
}


-- **************************************************************
--
-- UE Context Release Command
--
-- **************************************************************


S1ap-UEContextReleaseCommand ::= SEQUENCE {
    s1ap-UEContextReleaseCommand-ies SEQUENCE (SIZE (0..s1ap-maxProtocolIEs)) OF S1ap-IE,
        ...
}


S1ap-UEContextReleaseCommand-IEs S1AP-PROTOCOL-IES ::= {
        { ID id-UE-S1AP-IDs                                CRITICALITY reject        TYPE S1ap-UE-S1AP-IDs                                        PRESENCE mandatory} |
        
        { ID id-Cause                                        CRITICALITY ignore        TYPE S1ap-Cause                                                PRESENCE mandatory} ,
        ...
}


-- **************************************************************
--
-- UE Context Release Complete
--
-- **************************************************************


S1ap-UEContextReleaseComplete ::= SEQUENCE {
    s1ap-UEContextReleaseComplete-ies SEQUENCE (SIZE (0..s1ap-maxProtocolIEs)) OF S1ap-IE,
        ...
}


S1ap-UEContextReleaseComplete-IEs S1AP-PROTOCOL-IES ::= {
        { ID id-MME-UE-S1AP-ID                                CRITICALITY ignore        TYPE S1ap-MME-UE-S1AP-ID                                PRESENCE mandatory} |
        { ID id-eNB-UE-S1AP-ID                                CRITICALITY ignore        TYPE S1ap-ENB-UE-S1AP-ID                                PRESENCE mandatory} |
        { ID id-CriticalityDiagnostics                CRITICALITY ignore        TYPE S1ap-CriticalityDiagnostics                PRESENCE optional },
        ...
}




-- **************************************************************
--
-- UE CONTEXT MODIFICATION ELEMENTARY PROCEDURE
--
-- **************************************************************


-- **************************************************************
--
-- UE Context Modification Request
--
-- **************************************************************


S1ap-UEContextModificationRequest ::= SEQUENCE {
    s1ap-UEContextModificationRequest-ies SEQUENCE (SIZE (0..s1ap-maxProtocolIEs)) OF S1ap-IE,
        ...
}


S1ap-UEContextModificationRequestIEs S1AP-PROTOCOL-IES ::= {        
        { ID id-MME-UE-S1AP-ID                                CRITICALITY reject        TYPE S1ap-MME-UE-S1AP-ID                                         PRESENCE mandatory}|
        { ID id-eNB-UE-S1AP-ID                                CRITICALITY reject        TYPE S1ap-ENB-UE-S1AP-ID                                        PRESENCE mandatory}|
        { ID id-SecurityKey                                        CRITICALITY reject        TYPE S1ap-SecurityKey                                         PRESENCE optional}|
        { ID id-SubscriberProfileIDforRFP        CRITICALITY ignore        TYPE S1ap-SubscriberProfileIDforRFP                PRESENCE optional}|
        { ID id-uEaggregateMaximumBitrate        CRITICALITY ignore        TYPE S1ap-UEAggregateMaximumBitrate                PRESENCE optional}|
        { ID id-CSFallbackIndicator                        CRITICALITY reject        TYPE S1ap-CSFallbackIndicator                        PRESENCE optional}|
        { ID id-UESecurityCapabilities                CRITICALITY reject        TYPE S1ap-UESecurityCapabilities                        PRESENCE optional}|
        { ID id-CSGMembershipStatus                        CRITICALITY ignore        TYPE S1ap-CSGMembershipStatus                        PRESENCE optional}|
        { ID id-RegisteredLAI                                CRITICALITY ignore        TYPE S1ap-LAI                                                        PRESENCE optional},
        ...
}
-- **************************************************************
--
-- UE Context Modification Response
--
-- **************************************************************


S1ap-UEContextModificationResponse ::= SEQUENCE {
    s1ap-UEContextModificationResponse-ies SEQUENCE (SIZE (0..s1ap-maxProtocolIEs)) OF S1ap-IE,
        ...
}


S1ap-UEContextModificationResponseIEs S1AP-PROTOCOL-IES ::= {        
        { ID id-MME-UE-S1AP-ID                                CRITICALITY ignore        TYPE S1ap-MME-UE-S1AP-ID                                PRESENCE mandatory }|
        { ID id-eNB-UE-S1AP-ID                                CRITICALITY ignore        TYPE S1ap-ENB-UE-S1AP-ID                                PRESENCE mandatory }|
        { ID id-CriticalityDiagnostics                CRITICALITY ignore        TYPE S1ap-CriticalityDiagnostics                PRESENCE optional },
        ...
}-- **************************************************************
--
-- UE Context Modification Failure
--
-- **************************************************************


S1ap-UEContextModificationFailure ::= SEQUENCE {
    s1ap-UEContextModificationFailure-ies SEQUENCE (SIZE (0..s1ap-maxProtocolIEs)) OF S1ap-IE,
        ...
}


S1ap-UEContextModificationFailureIEs S1AP-PROTOCOL-IES ::= {        
        { ID id-MME-UE-S1AP-ID                                CRITICALITY ignore        TYPE S1ap-MME-UE-S1AP-ID                                PRESENCE mandatory }|
        { ID id-eNB-UE-S1AP-ID                                CRITICALITY ignore        TYPE S1ap-ENB-UE-S1AP-ID                                PRESENCE mandatory }|
        { ID id-Cause                                                CRITICALITY ignore        TYPE S1ap-Cause                                                PRESENCE mandatory }|
        { ID id-CriticalityDiagnostics                CRITICALITY ignore        TYPE S1ap-CriticalityDiagnostics                PRESENCE optional },
        ...
}


-- **************************************************************
--
-- NAS TRANSPORT ELEMENTARY PROCEDURES
--
-- **************************************************************


-- **************************************************************
--
-- DOWNLINK NAS TRANSPORT
--
-- **************************************************************


S1ap-DownlinkNASTransport ::= SEQUENCE {
    s1ap-DownlinkNASTransport-ies SEQUENCE (SIZE (0..s1ap-maxProtocolIEs)) OF S1ap-IE,
        ...
}


S1ap-DownlinkNASTransport-IEs S1AP-PROTOCOL-IES ::= {
        { ID id-MME-UE-S1AP-ID                                CRITICALITY reject        TYPE S1ap-MME-UE-S1AP-ID                                        PRESENCE mandatory} |
        { ID id-eNB-UE-S1AP-ID                                CRITICALITY reject        TYPE S1ap-ENB-UE-S1AP-ID                                        PRESENCE mandatory} |
        { ID id-NAS-PDU                                                CRITICALITY reject        TYPE S1ap-NAS-PDU                                                PRESENCE mandatory} |
        { ID id-HandoverRestrictionList                CRITICALITY ignore        TYPE S1ap-HandoverRestrictionList                PRESENCE optional} |
        { ID id-SubscriberProfileIDforRFP        CRITICALITY ignore        TYPE S1ap-SubscriberProfileIDforRFP                PRESENCE optional},
        ...
}




-- **************************************************************
--
-- INITIAL UE MESSAGE
--
-- **************************************************************


S1ap-InitialUEMessage ::= SEQUENCE {
    s1ap-InitialUEMessage-ies SEQUENCE (SIZE (0..s1ap-maxProtocolIEs)) OF S1ap-IE,
        ...
}


S1ap-InitialUEMessage-IEs S1AP-PROTOCOL-IES ::= {
        { ID id-eNB-UE-S1AP-ID                                CRITICALITY reject        TYPE S1ap-ENB-UE-S1AP-ID                                        PRESENCE mandatory} |
        { ID id-NAS-PDU                                                CRITICALITY reject        TYPE S1ap-NAS-PDU                                                PRESENCE mandatory} |
        { ID id-TAI                                                        CRITICALITY reject        TYPE S1ap-TAI                                                        PRESENCE mandatory} |
        { ID id-EUTRAN-CGI                                        CRITICALITY ignore        TYPE S1ap-EUTRAN-CGI                                                PRESENCE mandatory} |
        { ID id-RRC-Establishment-Cause                CRITICALITY ignore        TYPE S1ap-RRC-Establishment-Cause                PRESENCE mandatory} |
        { ID id-S-TMSI                                                CRITICALITY reject        TYPE S1ap-S-TMSI                                                        PRESENCE optional} |
        { ID id-CSG-Id                                                CRITICALITY reject        TYPE S1ap-CSG-Id                                                        PRESENCE optional} |
        { ID id-GUMMEI-ID                                        CRITICALITY reject        TYPE S1ap-GUMMEI                                                        PRESENCE optional} |
        { ID id-CellAccessMode                                CRITICALITY reject        TYPE S1ap-CellAccessMode                                        PRESENCE optional} |
        { ID id-GW-TransportLayerAddress        CRITICALITY ignore        TYPE S1ap-TransportLayerAddress                        PRESENCE optional} |
        { ID id-RelayNode-Indicator                        CRITICALITY reject        TYPE S1ap-RelayNode-Indicator                        PRESENCE optional},
        ...
}




-- **************************************************************
--
-- UPLINK NAS TRANSPORT
--
-- **************************************************************


S1ap-UplinkNASTransport ::= SEQUENCE {
    s1ap-UplinkNASTransport-ies SEQUENCE (SIZE (0..s1ap-maxProtocolIEs)) OF S1ap-IE,
        ...
}


S1ap-UplinkNASTransport-IEs S1AP-PROTOCOL-IES ::= {
        { ID id-MME-UE-S1AP-ID                                CRITICALITY reject        TYPE S1ap-MME-UE-S1AP-ID                                PRESENCE mandatory} |
        { ID id-eNB-UE-S1AP-ID                                CRITICALITY reject        TYPE S1ap-ENB-UE-S1AP-ID                                PRESENCE mandatory} |
        { ID id-NAS-PDU                                                CRITICALITY reject        TYPE S1ap-NAS-PDU                                        PRESENCE mandatory} |
        { ID id-EUTRAN-CGI                                        CRITICALITY ignore        TYPE S1ap-EUTRAN-CGI                                        PRESENCE mandatory} |
        { ID id-TAI                                                        CRITICALITY ignore        TYPE S1ap-TAI                                                PRESENCE mandatory} |
        { ID id-GW-TransportLayerAddress        CRITICALITY ignore        TYPE S1ap-TransportLayerAddress                PRESENCE optional},
        ...
}
-- **************************************************************
--
-- NAS NON DELIVERY INDICATION
--
-- **************************************************************


S1ap-NASNonDeliveryIndication ::= SEQUENCE {
    s1ap-NASNonDeliveryIndication-ies SEQUENCE (SIZE (0..s1ap-maxProtocolIEs)) OF S1ap-IE,
        ...
}


S1ap-NASNonDeliveryIndication-IEs S1AP-PROTOCOL-IES ::= {
        { ID id-MME-UE-S1AP-ID                        CRITICALITY reject        TYPE S1ap-MME-UE-S1AP-ID                                PRESENCE mandatory} |
        { ID id-eNB-UE-S1AP-ID                        CRITICALITY reject        TYPE S1ap-ENB-UE-S1AP-ID                                PRESENCE mandatory} |
        { ID id-NAS-PDU                                        CRITICALITY ignore        TYPE S1ap-NAS-PDU                                PRESENCE mandatory} |
        { ID id-Cause                                        CRITICALITY ignore        TYPE S1ap-Cause                                PRESENCE mandatory} ,
        ...
}


-- **************************************************************
--
-- RESET ELEMENTARY PROCEDURE
--
-- **************************************************************


-- **************************************************************
--
-- S1ap-Reset
--
-- **************************************************************


S1ap-Reset ::= SEQUENCE {
    s1ap-Reset-ies SEQUENCE (SIZE (0..s1ap-maxProtocolIEs)) OF S1ap-IE,
        ...
}


S1ap-ResetIEs S1AP-PROTOCOL-IES ::= {
        { ID id-Cause                                                CRITICALITY ignore        TYPE S1ap-Cause                                                PRESENCE mandatory        }|
        { ID id-ResetType                                CRITICALITY reject        TYPE S1ap-ResetType                        PRESENCE mandatory        },
        ...
}


S1ap-ResetType ::= CHOICE {
        s1-Interface                S1ap-ResetAll,
        partOfS1-Interface                S1ap-UE-associatedLogicalS1-ConnectionListRes,
        ...
}






S1ap-ResetAll ::= ENUMERATED {
        reset-all,
        ...
}


S1ap-UE-associatedLogicalS1-ConnectionListRes ::= SEQUENCE (SIZE(1.. s1ap-maxNrOfIndividualS1ConnectionsToReset)) OF ProtocolIE-SingleContainer { { S1ap-UE-associatedLogicalS1-ConnectionItemRes } }


S1ap-UE-associatedLogicalS1-ConnectionItemRes         S1AP-PROTOCOL-IES ::= {
        { ID id-UE-associatedLogicalS1-ConnectionItem         CRITICALITY reject         TYPE S1ap-UE-associatedLogicalS1-ConnectionItem         PRESENCE mandatory },
        ...
}




-- **************************************************************
--
-- S1ap-Reset Acknowledge
--
-- **************************************************************


S1ap-ResetAcknowledge ::= SEQUENCE {
    s1ap-ResetAcknowledge-ies SEQUENCE (SIZE (0..s1ap-maxProtocolIEs)) OF S1ap-IE,
        ...
}


S1ap-ResetAcknowledgeIEs S1AP-PROTOCOL-IES ::= {
        { ID id-UE-associatedLogicalS1-ConnectionListResAck                CRITICALITY ignore        TYPE S1ap-UE-associatedLogicalS1-ConnectionListResAck                        PRESENCE optional        }|
        { ID id-CriticalityDiagnostics                CRITICALITY ignore        TYPE S1ap-CriticalityDiagnostics                        PRESENCE optional        },
        ...
}


S1ap-UE-associatedLogicalS1-ConnectionListResAck ::= SEQUENCE (SIZE(1.. s1ap-maxNrOfIndividualS1ConnectionsToReset)) OF ProtocolIE-SingleContainer { { S1ap-UE-associatedLogicalS1-ConnectionItemResAck } }


S1ap-UE-associatedLogicalS1-ConnectionItemResAck         S1AP-PROTOCOL-IES ::= {
        { ID id-UE-associatedLogicalS1-ConnectionItem         CRITICALITY ignore         TYPE S1ap-UE-associatedLogicalS1-ConnectionItem          PRESENCE mandatory },
        ...
}


-- **************************************************************
--
-- ERROR INDICATION ELEMENTARY PROCEDURE
--
-- **************************************************************


-- **************************************************************
--
-- Error Indication
--
-- **************************************************************


S1ap-ErrorIndication ::= SEQUENCE {
    s1ap-ErrorIndication-ies SEQUENCE (SIZE (0..s1ap-maxProtocolIEs)) OF S1ap-IE,
        ...
}


S1ap-ErrorIndicationIEs S1AP-PROTOCOL-IES ::= {
        { ID id-MME-UE-S1AP-ID                                CRITICALITY ignore        TYPE S1ap-MME-UE-S1AP-ID                                PRESENCE optional        } |
        { ID id-eNB-UE-S1AP-ID                                CRITICALITY ignore        TYPE S1ap-ENB-UE-S1AP-ID                                PRESENCE optional        } |
        { ID id-Cause                                                CRITICALITY ignore        TYPE S1ap-Cause                                                PRESENCE optional        } |
        { ID id-CriticalityDiagnostics                CRITICALITY ignore        TYPE S1ap-CriticalityDiagnostics                PRESENCE optional        } ,
        ...
}


-- **************************************************************
--
-- S1 SETUP ELEMENTARY PROCEDURE
--
-- **************************************************************


-- **************************************************************
--
-- S1 Setup Request
--
-- **************************************************************


S1ap-S1SetupRequest ::= SEQUENCE {
    s1ap-S1SetupRequest-ies SEQUENCE (SIZE (0..s1ap-maxProtocolIEs)) OF S1ap-IE,
        ...
}


S1ap-S1SetupRequestIEs S1AP-PROTOCOL-IES ::= {
        { ID id-Global-ENB-ID        CRITICALITY reject        TYPE S1ap-Global-ENB-ID        PRESENCE mandatory}|
        { ID id-eNBname        CRITICALITY ignore        TYPE S1ap-ENBname        PRESENCE optional}|
        { ID id-SupportedTAs        CRITICALITY reject        TYPE S1ap-SupportedTAs        PRESENCE mandatory}|
        { ID id-DefaultPagingDRX        CRITICALITY ignore        TYPE S1ap-PagingDRX        PRESENCE mandatory}|
        { ID id-CSG-IdList        CRITICALITY reject        TYPE S1ap-CSG-IdList        PRESENCE optional},
        ...
}


-- **************************************************************
--
-- S1 Setup Response
--
-- **************************************************************


S1ap-S1SetupResponse ::= SEQUENCE {
    s1ap-S1SetupResponse-ies SEQUENCE (SIZE (0..s1ap-maxProtocolIEs)) OF S1ap-IE,
        ...
}




S1ap-S1SetupResponseIEs S1AP-PROTOCOL-IES ::= {
        { ID id-MMEname                                                CRITICALITY ignore        TYPE S1ap-MMEname                                                PRESENCE optional}|
        { ID id-ServedGUMMEIs                                CRITICALITY reject        TYPE S1ap-ServedGUMMEIs                                        PRESENCE mandatory}|
        { ID id-RelativeMMECapacity                        CRITICALITY ignore        TYPE S1ap-RelativeMMECapacity                        PRESENCE mandatory}|
        { ID id-MMERelaySupportIndicator        CRITICALITY ignore        TYPE S1ap-MMERelaySupportIndicator                PRESENCE optional}|
        { ID id-CriticalityDiagnostics                CRITICALITY ignore        TYPE S1ap-CriticalityDiagnostics                        PRESENCE optional},
        ...
}


-- **************************************************************
--
-- S1 Setup Failure
--
-- **************************************************************


S1ap-S1SetupFailure ::= SEQUENCE {
    s1ap-S1SetupFailure-ies SEQUENCE (SIZE (0..s1ap-maxProtocolIEs)) OF S1ap-IE,
        ...
}


S1ap-S1SetupFailureIEs S1AP-PROTOCOL-IES ::= {
        { ID id-Cause                                                CRITICALITY ignore        TYPE S1ap-Cause                                                PRESENCE mandatory        }|
        { ID id-TimeToWait                                        CRITICALITY ignore        TYPE S1ap-TimeToWait                                        PRESENCE optional        }|
        { ID id-CriticalityDiagnostics                CRITICALITY ignore        TYPE S1ap-CriticalityDiagnostics                        PRESENCE optional        },
        ...
}


-- **************************************************************
--
-- ENB CONFIGURATION UPDATE ELEMENTARY PROCEDURE
--
-- **************************************************************


-- **************************************************************
--
-- eNB Configuration Update 
--
-- **************************************************************


S1ap-ENBConfigurationUpdate ::= SEQUENCE {
    s1ap-ENBConfigurationUpdate-ies SEQUENCE (SIZE (0..s1ap-maxProtocolIEs)) OF S1ap-IE,
        ...
}


S1ap-ENBConfigurationUpdateIEs S1AP-PROTOCOL-IES ::= {
        { ID id-eNBname                                CRITICALITY ignore        TYPE S1ap-ENBname                        PRESENCE optional        }|
        { ID id-SupportedTAs                CRITICALITY reject        TYPE S1ap-SupportedTAs                 PRESENCE optional        }|
        { ID id-CSG-IdList                                        CRITICALITY reject        TYPE S1ap-CSG-IdList                                PRESENCE optional}|
        { ID id-DefaultPagingDRX        CRITICALITY        ignore        TYPE S1ap-PagingDRX                PRESENCE optional        },
        ...
}


-- **************************************************************
--
-- eNB Configuration Update Acknowledge
--
-- **************************************************************


S1ap-ENBConfigurationUpdateAcknowledge ::= SEQUENCE {
    s1ap-ENBConfigurationUpdateAcknowledge-ies SEQUENCE (SIZE (0..s1ap-maxProtocolIEs)) OF S1ap-IE,
        ...
}




S1ap-ENBConfigurationUpdateAcknowledgeIEs S1AP-PROTOCOL-IES ::= {
        { ID id-CriticalityDiagnostics                CRITICALITY ignore        TYPE S1ap-CriticalityDiagnostics                        PRESENCE optional        },
        ...
}


-- **************************************************************
--
-- eNB Configuration Update Failure
--
-- **************************************************************


S1ap-ENBConfigurationUpdateFailure ::= SEQUENCE {
    s1ap-ENBConfigurationUpdateFailure-ies SEQUENCE (SIZE (0..s1ap-maxProtocolIEs)) OF S1ap-IE,
        ...
}


S1ap-ENBConfigurationUpdateFailureIEs S1AP-PROTOCOL-IES ::= {
        { ID id-Cause                                                CRITICALITY ignore        TYPE S1ap-Cause                                                PRESENCE mandatory        }|
        { ID id-TimeToWait                                        CRITICALITY ignore        TYPE S1ap-TimeToWait                                        PRESENCE optional        }|
        { ID id-CriticalityDiagnostics                CRITICALITY ignore        TYPE S1ap-CriticalityDiagnostics        PRESENCE optional },
...
}




-- **************************************************************
--
-- MME Configuration UPDATE ELEMENTARY PROCEDURE
--
-- **************************************************************


-- **************************************************************
--
-- MME Configuration Update 
--
-- **************************************************************


S1ap-MMEConfigurationUpdate ::= SEQUENCE {
    s1ap-MMEConfigurationUpdate-ies SEQUENCE (SIZE (0..s1ap-maxProtocolIEs)) OF S1ap-IE,
        ...
}


S1ap-MMEConfigurationUpdateIEs S1AP-PROTOCOL-IES ::= {
        { ID id-MMEname                                CRITICALITY ignore        TYPE S1ap-MMEname                         PRESENCE optional        }|
        { ID id-ServedGUMMEIs                        CRITICALITY reject        TYPE S1ap-ServedGUMMEIs                                PRESENCE optional        }|
        { ID id-RelativeMMECapacity        CRITICALITY reject        TYPE S1ap-RelativeMMECapacity        PRESENCE optional},
        ...
}


-- **************************************************************
--
-- MME Configuration Update Acknowledge
--
-- **************************************************************


S1ap-MMEConfigurationUpdateAcknowledge ::= SEQUENCE {
    s1ap-MMEConfigurationUpdateAcknowledge-ies SEQUENCE (SIZE (0..s1ap-maxProtocolIEs)) OF S1ap-IE,
        ...
}




S1ap-MMEConfigurationUpdateAcknowledgeIEs S1AP-PROTOCOL-IES ::= {
        { ID id-CriticalityDiagnostics                CRITICALITY ignore        TYPE S1ap-CriticalityDiagnostics                        PRESENCE optional        },
        ...
}


-- **************************************************************
--
-- MME Configuration Update Failure
--
-- **************************************************************


S1ap-MMEConfigurationUpdateFailure ::= SEQUENCE {
    s1ap-MMEConfigurationUpdateFailure-ies SEQUENCE (SIZE (0..s1ap-maxProtocolIEs)) OF S1ap-IE,
        ...
}


S1ap-MMEConfigurationUpdateFailureIEs S1AP-PROTOCOL-IES ::= {
        { ID id-Cause                                                CRITICALITY ignore        TYPE S1ap-Cause                                                PRESENCE mandatory        }|
        { ID id-TimeToWait                                        CRITICALITY ignore        TYPE S1ap-TimeToWait                                        PRESENCE optional        }|
        { ID id-CriticalityDiagnostics                CRITICALITY ignore        TYPE S1ap-CriticalityDiagnostics                        PRESENCE optional        },
        ...
}


-- **************************************************************
--
-- DOWNLINK S1 CDMA2000 TUNNELING ELEMENTARY PROCEDURE
--
-- **************************************************************


-- **************************************************************
--
-- Downlink S1 CDMA2000 Tunneling
--
-- **************************************************************


S1ap-DownlinkS1cdma2000tunneling ::= SEQUENCE {
    s1ap-DownlinkS1cdma2000tunneling-ies SEQUENCE (SIZE (0..s1ap-maxProtocolIEs)) OF S1ap-IE,
        ...
}


S1ap-DownlinkS1cdma2000tunnelingIEs S1AP-PROTOCOL-IES ::= {
        { ID id-MME-UE-S1AP-ID                                CRITICALITY reject        TYPE S1ap-MME-UE-S1AP-ID                                PRESENCE mandatory        } |
        { ID id-eNB-UE-S1AP-ID                                CRITICALITY reject        TYPE S1ap-ENB-UE-S1AP-ID                                PRESENCE mandatory        } |
        { ID id-E-RABDataForwardingList                CRITICALITY ignore        TYPE S1ap-E-RABDataForwardingList                                         PRESENCE optional        } |
        { ID id-cdma2000HOStatus                                CRITICALITY ignore        TYPE S1ap-Cdma2000HOStatus                         PRESENCE optional        } |
        { ID id-cdma2000RATType                                CRITICALITY reject        TYPE S1ap-Cdma2000RATType                         PRESENCE mandatory        } |
        { ID id-cdma2000PDU                                        CRITICALITY reject        TYPE S1ap-Cdma2000PDU                                 PRESENCE mandatory        },
        ...
}


-- **************************************************************
--
-- UPLINK S1 CDMA2000 TUNNELING ELEMENTARY PROCEDURE
--
-- **************************************************************


-- **************************************************************
--
-- Uplink S1 CDMA2000 Tunneling
--
-- **************************************************************


S1ap-UplinkS1cdma2000tunneling ::= SEQUENCE {
    s1ap-UplinkS1cdma2000tunneling-ies SEQUENCE (SIZE (0..s1ap-maxProtocolIEs)) OF S1ap-IE,
        ...
}


S1ap-UplinkS1cdma2000tunnelingIEs S1AP-PROTOCOL-IES ::= {
        { ID id-MME-UE-S1AP-ID                                CRITICALITY reject        TYPE S1ap-MME-UE-S1AP-ID                                PRESENCE mandatory        } |
        { ID id-eNB-UE-S1AP-ID                                CRITICALITY reject        TYPE S1ap-ENB-UE-S1AP-ID                                PRESENCE mandatory        } |
        { ID id-cdma2000RATType                                CRITICALITY reject        TYPE S1ap-Cdma2000RATType                         PRESENCE mandatory        } |
        { ID id-cdma2000SectorID                        CRITICALITY reject        TYPE S1ap-Cdma2000SectorID                         PRESENCE mandatory        } |
        { ID id-cdma2000HORequiredIndication        CRITICALITY ignore        TYPE S1ap-Cdma2000HORequiredIndication                         PRESENCE optional        } |
        { ID id-cdma2000OneXSRVCCInfo                CRITICALITY reject        TYPE S1ap-Cdma2000OneXSRVCCInfo                         PRESENCE optional        } |
        { ID id-cdma2000OneXRAND                        CRITICALITY reject        TYPE S1ap-Cdma2000OneXRAND                         PRESENCE optional        } |
        { ID id-cdma2000PDU                                        CRITICALITY reject        TYPE S1ap-Cdma2000PDU                                 PRESENCE mandatory        }|
        { ID id-EUTRANRoundTripDelayEstimationInfo        CRITICALITY ignore        TYPE S1ap-EUTRANRoundTripDelayEstimationInfo                PRESENCE optional},
        -- Extension for Release 9 to assist target HRPD access with the acquisition of the UE --
        ...
}




-- **************************************************************
--
-- UE CAPABILITY INFO INDICATION ELEMENTARY PROCEDURE
--
-- **************************************************************


-- **************************************************************
--
-- UE Capability Info Indication
--
-- **************************************************************


S1ap-UECapabilityInfoIndication ::= SEQUENCE {
    s1ap-UECapabilityInfoIndication-ies SEQUENCE (SIZE (0..s1ap-maxProtocolIEs)) OF S1ap-IE,
        ...
}


S1ap-UECapabilityInfoIndicationIEs S1AP-PROTOCOL-IES ::= {
        { ID id-MME-UE-S1AP-ID                                CRITICALITY reject        TYPE S1ap-MME-UE-S1AP-ID                                         PRESENCE mandatory        } |
        { ID id-eNB-UE-S1AP-ID                                CRITICALITY reject        TYPE S1ap-ENB-UE-S1AP-ID                                         PRESENCE mandatory        } |
        { ID id-UERadioCapability                        CRITICALITY ignore        TYPE S1ap-UERadioCapability                                PRESENCE mandatory        } ,
        ...
}


-- **************************************************************
--
-- eNB STATUS TRANSFER ELEMENTARY PROCEDURE
--
-- **************************************************************


-- **************************************************************
--
-- eNB Status Transfer
--
-- **************************************************************


S1ap-ENBStatusTransfer ::= SEQUENCE {
    s1ap-ENBStatusTransfer-ies SEQUENCE (SIZE (0..s1ap-maxProtocolIEs)) OF S1ap-IE,
        ...
}


S1ap-ENBStatusTransferIEs S1AP-PROTOCOL-IES ::= {
        { ID id-MME-UE-S1AP-ID                        CRITICALITY reject        TYPE S1ap-MME-UE-S1AP-ID                                PRESENCE mandatory} |
        { ID id-eNB-UE-S1AP-ID                        CRITICALITY reject        TYPE S1ap-ENB-UE-S1AP-ID                                PRESENCE mandatory} |
        { ID id-eNB-StatusTransfer-TransparentContainer        CRITICALITY reject        TYPE S1ap-ENB-StatusTransfer-TransparentContainer                PRESENCE mandatory} ,
        ...
}




-- **************************************************************
--
-- MME STATUS TRANSFER ELEMENTARY PROCEDURE
--
-- **************************************************************


-- **************************************************************
--
-- MME Status Transfer
--
-- **************************************************************


S1ap-MMEStatusTransfer ::= SEQUENCE {
    s1ap-MMEStatusTransfer-ies SEQUENCE (SIZE (0..s1ap-maxProtocolIEs)) OF S1ap-IE,
        ...
}


S1ap-MMEStatusTransferIEs S1AP-PROTOCOL-IES ::= {
        { ID id-MME-UE-S1AP-ID                        CRITICALITY reject        TYPE S1ap-MME-UE-S1AP-ID                                PRESENCE mandatory} |
        { ID id-eNB-UE-S1AP-ID                        CRITICALITY reject        TYPE S1ap-ENB-UE-S1AP-ID                                PRESENCE mandatory} |
        { ID id-eNB-StatusTransfer-TransparentContainer        CRITICALITY reject        TYPE S1ap-ENB-StatusTransfer-TransparentContainer                PRESENCE mandatory} ,
        ...
}




-- **************************************************************
--
-- TRACE ELEMENTARY PROCEDURES
--
-- **************************************************************
-- **************************************************************
--
-- Trace Start
--
-- **************************************************************


S1ap-TraceStart ::= SEQUENCE {
    s1ap-TraceStart-ies SEQUENCE (SIZE (0..s1ap-maxProtocolIEs)) OF S1ap-IE,
        ...
}


S1ap-TraceStartIEs S1AP-PROTOCOL-IES ::= {
        { ID id-MME-UE-S1AP-ID                                CRITICALITY reject        TYPE S1ap-MME-UE-S1AP-ID                                PRESENCE mandatory} |
        { ID id-eNB-UE-S1AP-ID                                CRITICALITY reject        TYPE S1ap-ENB-UE-S1AP-ID                                PRESENCE mandatory} |
        { ID id-TraceActivation                                CRITICALITY ignore        TYPE S1ap-TraceActivation                        PRESENCE mandatory        },
        ...
}


-- **************************************************************
--
-- Trace Failure Indication
--
-- **************************************************************


S1ap-TraceFailureIndication ::= SEQUENCE {
    s1ap-TraceFailureIndication-ies SEQUENCE (SIZE (0..s1ap-maxProtocolIEs)) OF S1ap-IE,
        ...
}


S1ap-TraceFailureIndicationIEs S1AP-PROTOCOL-IES ::= {
        { ID id-MME-UE-S1AP-ID                                CRITICALITY reject        TYPE S1ap-MME-UE-S1AP-ID                                PRESENCE mandatory} |
        { ID id-eNB-UE-S1AP-ID                                CRITICALITY reject        TYPE S1ap-ENB-UE-S1AP-ID                                PRESENCE mandatory} |
        { ID id-E-UTRAN-Trace-ID                        CRITICALITY ignore        TYPE S1ap-E-UTRAN-Trace-ID                        PRESENCE mandatory} |
        { ID id-Cause                                                CRITICALITY ignore        TYPE S1ap-Cause                                                PRESENCE mandatory} ,
        ...
}


-- **************************************************************
--
-- DEACTIVATE TRACE ELEMENTARY PROCEDURE
--
-- **************************************************************


-- **************************************************************
--
-- DEACTIVATE TRACE
--
-- **************************************************************


S1ap-DeactivateTrace ::= SEQUENCE {
    s1ap-DeactivateTrace-ies SEQUENCE (SIZE (0..s1ap-maxProtocolIEs)) OF S1ap-IE,
        ...
}


S1ap-DeactivateTraceIEs S1AP-PROTOCOL-IES ::= {
        { ID id-MME-UE-S1AP-ID                CRITICALITY reject        TYPE S1ap-MME-UE-S1AP-ID                PRESENCE mandatory} |
        { ID id-eNB-UE-S1AP-ID                CRITICALITY reject        TYPE S1ap-ENB-UE-S1AP-ID                PRESENCE mandatory} |
        { ID id-E-UTRAN-Trace-ID                CRITICALITY ignore        TYPE S1ap-E-UTRAN-Trace-ID                 PRESENCE mandatory        },
        ...
}


-- **************************************************************
--
-- CELL TRAFFIC TRACE ELEMENTARY PROCEDURE
--
-- **************************************************************


-- **************************************************************
--
-- CELL TRAFFIC TRACE
--
-- **************************************************************


S1ap-CellTrafficTrace ::= SEQUENCE {
    s1ap-CellTrafficTrace-ies SEQUENCE (SIZE (0..s1ap-maxProtocolIEs)) OF S1ap-IE,
     ...
}


S1ap-CellTrafficTraceIEs S1AP-PROTOCOL-IES ::= {
        {ID id-MME-UE-S1AP-ID                                        CRITICALITY reject        TYPE S1ap-MME-UE-S1AP-ID                                PRESENCE mandatory}|
        {ID id-eNB-UE-S1AP-ID                                        CRITICALITY reject        TYPE S1ap-ENB-UE-S1AP-ID                                PRESENCE mandatory}|
        {ID id-E-UTRAN-Trace-ID                                        CRITICALITY ignore        TYPE S1ap-E-UTRAN-Trace-ID                        PRESENCE mandatory}|
        {ID id-EUTRAN-CGI                                                CRITICALITY ignore        TYPE S1ap-EUTRAN-CGI                                        PRESENCE mandatory}|
        {ID id-TraceCollectionEntityIPAddress        CRITICALITY ignore        TYPE S1ap-TransportLayerAddress                PRESENCE mandatory}|
        {ID id-PrivacyIndicator                                        CRITICALITY ignore        TYPE S1ap-PrivacyIndicator                        PRESENCE optional},
        ...
}


-- **************************************************************
--
-- LOCATION ELEMENTARY PROCEDURES
--
-- **************************************************************


-- **************************************************************
--
-- Location Reporting Control
--
-- **************************************************************


S1ap-LocationReportingControl ::= SEQUENCE {
    s1ap-LocationReportingControl-ies SEQUENCE (SIZE (0..s1ap-maxProtocolIEs)) OF S1ap-IE,
        ...
}


S1ap-LocationReportingControlIEs S1AP-PROTOCOL-IES ::= {
        { ID id-MME-UE-S1AP-ID                        CRITICALITY reject        TYPE S1ap-MME-UE-S1AP-ID                                PRESENCE mandatory} |
        { ID id-eNB-UE-S1AP-ID                        CRITICALITY reject        TYPE S1ap-ENB-UE-S1AP-ID                                PRESENCE mandatory} |
        { ID id-RequestType                                CRITICALITY ignore        TYPE S1ap-RequestType                                PRESENCE mandatory        } ,
        ...
}


-- **************************************************************
--
-- Location Report Failure Indication
--
-- **************************************************************


S1ap-LocationReportingFailureIndication ::= SEQUENCE {
    s1ap-LocationReportingFailureIndication-ies SEQUENCE (SIZE (0..s1ap-maxProtocolIEs)) OF S1ap-IE,
        ...
}


S1ap-LocationReportingFailureIndicationIEs S1AP-PROTOCOL-IES ::= {
        { ID id-MME-UE-S1AP-ID                        CRITICALITY reject        TYPE S1ap-MME-UE-S1AP-ID                                PRESENCE mandatory} |
        { ID id-eNB-UE-S1AP-ID                        CRITICALITY reject        TYPE S1ap-ENB-UE-S1AP-ID                                PRESENCE mandatory} |
        { ID id-Cause                                        CRITICALITY ignore        TYPE S1ap-Cause                                                PRESENCE mandatory},
        ...
}


-- **************************************************************
--
-- Location Report 
--
-- **************************************************************


S1ap-LocationReport ::= SEQUENCE {
    s1ap-LocationReport-ies SEQUENCE (SIZE (0..s1ap-maxProtocolIEs)) OF S1ap-IE,
        ...
}


S1ap-LocationReportIEs S1AP-PROTOCOL-IES ::= {
        { ID id-MME-UE-S1AP-ID                        CRITICALITY reject        TYPE S1ap-MME-UE-S1AP-ID                                PRESENCE mandatory} |
        { ID id-eNB-UE-S1AP-ID                        CRITICALITY reject        TYPE S1ap-ENB-UE-S1AP-ID                                PRESENCE mandatory} |
        { ID id-EUTRAN-CGI                                CRITICALITY ignore        TYPE S1ap-EUTRAN-CGI                                        PRESENCE mandatory} |
        { ID id-TAI                                                CRITICALITY ignore        TYPE S1ap-TAI                                                PRESENCE mandatory} |
        { ID id-RequestType                                CRITICALITY ignore        TYPE S1ap-RequestType                                PRESENCE mandatory} ,
        ...
}


-- **************************************************************
--
-- OVERLOAD ELEMENTARY PROCEDURES
--
-- **************************************************************


-- **************************************************************
--
-- Overload Start
--
-- **************************************************************


S1ap-OverloadStart ::= SEQUENCE {
    s1ap-OverloadStart-ies SEQUENCE (SIZE (0..s1ap-maxProtocolIEs)) OF S1ap-IE,
        ...
}


S1ap-OverloadStartIEs S1AP-PROTOCOL-IES ::= {        
        { ID id-OverloadResponse                                        CRITICALITY reject        TYPE S1ap-OverloadResponse                                PRESENCE mandatory}|
        { ID id-GUMMEIList                                                        CRITICALITY ignore        TYPE S1ap-GUMMEIList                                                PRESENCE optional}|
        { ID id-TrafficLoadReductionIndication                CRITICALITY ignore        TYPE S1ap-TrafficLoadReductionIndication        PRESENCE optional},
        ...
}
-- **************************************************************
--
-- Overload Stop
--
-- **************************************************************


S1ap-OverloadStop ::= SEQUENCE {
    s1ap-OverloadStop-ies SEQUENCE (SIZE (0..s1ap-maxProtocolIEs)) OF S1ap-IE,
        ...
}


S1ap-OverloadStopIEs S1AP-PROTOCOL-IES ::= {        
{ ID id-GUMMEIList                                                        CRITICALITY ignore        TYPE S1ap-GUMMEIList                                PRESENCE optional },
        ...
}
-- **************************************************************
--
-- WRITE-REPLACE WARNING ELEMENTARY PROCEDURE 
--
-- **************************************************************


-- **************************************************************
--
-- Write-Replace Warning Request
--
-- **************************************************************




S1ap-WriteReplaceWarningRequest ::= SEQUENCE {
    s1ap-WriteReplaceWarningRequest-ies SEQUENCE (SIZE (0..s1ap-maxProtocolIEs)) OF S1ap-IE,
        ...
}


S1ap-WriteReplaceWarningRequestIEs S1AP-PROTOCOL-IES ::= {        
        { ID id-MessageIdentifier                        CRITICALITY reject        TYPE S1ap-MessageIdentifier                PRESENCE mandatory                }|
        { ID id-SerialNumber                                CRITICALITY reject        TYPE S1ap-SerialNumber                        PRESENCE mandatory                }|
        { ID id-WarningAreaList                                CRITICALITY ignore        TYPE S1ap-WarningAreaList                PRESENCE optional                }|
        { ID id-RepetitionPeriod                        CRITICALITY reject        TYPE S1ap-RepetitionPeriod                PRESENCE mandatory                }|
        { ID id-ExtendedRepetitionPeriod        CRITICALITY reject        TYPE S1ap-ExtendedRepetitionPeriod        PRESENCE optional        }|
        { ID id-NumberofBroadcastRequest        CRITICALITY reject        TYPE S1ap-NumberofBroadcastRequest        PRESENCE mandatory        }|
        { ID id-WarningType                                        CRITICALITY ignore        TYPE S1ap-WarningType                        PRESENCE optional                }|
        { ID id-WarningSecurityInfo                        CRITICALITY ignore        TYPE S1ap-WarningSecurityInfo        PRESENCE optional                }|
        { ID id-DataCodingScheme                        CRITICALITY ignore        TYPE S1ap-DataCodingScheme                PRESENCE optional                }|
        { ID id-WarningMessageContents                CRITICALITY ignore        TYPE S1ap-WarningMessageContents                PRESENCE optional                }|
        { ID id-ConcurrentWarningMessageIndicator        CRITICALITY reject        TYPE S1ap-ConcurrentWarningMessageIndicator                PRESENCE optional                },
        ...
}
-- **************************************************************
--
-- Write-Replace Warning Response
--
-- **************************************************************


S1ap-WriteReplaceWarningResponse ::= SEQUENCE {
    s1ap-WriteReplaceWarningResponse-ies SEQUENCE (SIZE (0..s1ap-maxProtocolIEs)) OF S1ap-IE,
        ...
}


S1ap-WriteReplaceWarningResponseIEs S1AP-PROTOCOL-IES ::= {
        { ID id-MessageIdentifier                        CRITICALITY reject        TYPE S1ap-MessageIdentifier                                        PRESENCE mandatory }|
        { ID id-SerialNumber                                CRITICALITY reject        TYPE S1ap-SerialNumber                                                PRESENCE mandatory }|
        { ID id-BroadcastCompletedAreaList        CRITICALITY ignore        TYPE S1ap-BroadcastCompletedAreaList                        PRESENCE optional        }|
        { ID id-CriticalityDiagnostics                CRITICALITY ignore        TYPE S1ap-CriticalityDiagnostics                                PRESENCE optional },
        ...
}


-- **************************************************************
--
-- eNB DIRECT INFORMATION TRANSFER ELEMENTARY PROCEDURE
--
-- **************************************************************


-- **************************************************************
--
-- eNB Direct Information Transfer
--
-- **************************************************************


S1ap-ENBDirectInformationTransfer ::= SEQUENCE {
    s1ap-ENBDirectInformationTransfer-ies SEQUENCE (SIZE (0..s1ap-maxProtocolIEs)) OF S1ap-IE,
        ...
}


S1ap-ENBDirectInformationTransferIEs S1AP-PROTOCOL-IES ::= {
        { ID id-Inter-SystemInformationTransferTypeEDT                CRITICALITY reject        TYPE S1ap-Inter-SystemInformationTransferType                        PRESENCE mandatory}  ,
        ...
}


S1ap-Inter-SystemInformationTransferType ::= CHOICE {
        rIMTransfer                S1ap-RIMTransfer,
        ...
}


-- **************************************************************
--
-- MME DIRECT INFORMATION TRANSFER ELEMENTARY PROCEDURE
--
-- **************************************************************


-- **************************************************************
--
-- MME Direct Information Transfer
--
-- **************************************************************


S1ap-MMEDirectInformationTransfer ::= SEQUENCE {
    s1ap-MMEDirectInformationTransfer-ies SEQUENCE (SIZE (0..s1ap-maxProtocolIEs)) OF S1ap-IE,
        ...
}


S1ap-MMEDirectInformationTransferIEs S1AP-PROTOCOL-IES ::= {
        { ID id-Inter-SystemInformationTransferTypeMDT                CRITICALITY reject        TYPE S1ap-Inter-SystemInformationTransferType                        PRESENCE mandatory}  ,
        ...
}
-- **************************************************************
--
-- eNB CONFIGURATION TRANSFER ELEMENTARY PROCEDURE
--
-- **************************************************************


-- **************************************************************
--
-- eNB Configuration Transfer
--
-- **************************************************************


S1ap-ENBConfigurationTransfer ::= SEQUENCE {
    s1ap-ENBConfigurationTransfer-ies SEQUENCE (SIZE (0..s1ap-maxProtocolIEs)) OF S1ap-IE,
        ...
}


S1ap-ENBConfigurationTransferIEs S1AP-PROTOCOL-IES ::= {
        { ID id-SONConfigurationTransferECT                CRITICALITY ignore        TYPE S1ap-SONConfigurationTransfer                                PRESENCE optional}  ,
        ...
}


-- **************************************************************
--
-- MME CONFIGURATION TRANSFER ELEMENTARY PROCEDURE
--
-- **************************************************************


-- **************************************************************
--
-- MME Configuration Transfer
--
-- **************************************************************


S1ap-MMEConfigurationTransfer ::= SEQUENCE {
    s1ap-MMEConfigurationTransfer-ies SEQUENCE (SIZE (0..s1ap-maxProtocolIEs)) OF S1ap-IE,
        ...
}


S1ap-MMEConfigurationTransferIEs S1AP-PROTOCOL-IES ::= {
        { ID id-SONConfigurationTransferMCT                CRITICALITY ignore        TYPE S1ap-SONConfigurationTransfer                                PRESENCE optional}  ,
        ...
}


-- **************************************************************
--
-- PRIVATE MESSAGE ELEMENTARY PROCEDURE
--
-- **************************************************************


-- **************************************************************
--
-- Private Message
--
-- **************************************************************


S1ap-PrivateMessage ::= SEQUENCE {
        privateIEs                        PrivateIE-Container       {{PrivateMessageIEs}},
        ...
}


PrivateMessageIEs S1AP-PRIVATE-IES ::= {
        ...
}


-- **************************************************************
--
-- Kill Request
--
-- **************************************************************




S1ap-KillRequest ::= SEQUENCE {
    s1ap-KillRequest-ies SEQUENCE (SIZE (0..s1ap-maxProtocolIEs)) OF S1ap-IE,
        ...
}


S1ap-KillRequestIEs S1AP-PROTOCOL-IES ::= {        
        { ID id-MessageIdentifier                        CRITICALITY reject        TYPE S1ap-MessageIdentifier                PRESENCE mandatory }|
        { ID id-SerialNumber                                CRITICALITY reject        TYPE S1ap-SerialNumber                        PRESENCE mandatory }|
        { ID id-WarningAreaList                                CRITICALITY ignore        TYPE S1ap-WarningAreaList                PRESENCE optional },
        ...
}


-- **************************************************************
--
-- Kill Response
--
-- **************************************************************


S1ap-KillResponse ::= SEQUENCE {
    s1ap-KillResponse-ies SEQUENCE (SIZE (0..s1ap-maxProtocolIEs)) OF S1ap-IE,
        ...
}


S1ap-KillResponseIEs S1AP-PROTOCOL-IES ::= {
        { ID id-MessageIdentifier                        CRITICALITY reject        TYPE S1ap-MessageIdentifier                                PRESENCE mandatory }|
        { ID id-SerialNumber                                CRITICALITY reject        TYPE S1ap-SerialNumber                                        PRESENCE mandatory }|
        { ID id-BroadcastCancelledAreaList        CRITICALITY ignore        TYPE S1ap-BroadcastCancelledAreaList                PRESENCE optional }|
        { ID id-CriticalityDiagnostics                CRITICALITY ignore        TYPE S1ap-CriticalityDiagnostics                        PRESENCE optional },
        ...
}


-- **************************************************************
--
-- LPPA TRANSPORT ELEMENTARY PROCEDURES
--
-- **************************************************************


-- **************************************************************
--
-- DOWNLINK UE ASSOCIATED LPPA TRANSPORT
--
-- **************************************************************


S1ap-DownlinkUEAssociatedLPPaTransport ::= SEQUENCE {
    s1ap-DownlinkUEAssociatedLPPaTransport-ies SEQUENCE (SIZE (0..s1ap-maxProtocolIEs)) OF S1ap-IE,
        ...
}


S1ap-DownlinkUEAssociatedLPPaTransport-IEs S1AP-PROTOCOL-IES ::= {
        { ID id-MME-UE-S1AP-ID                        CRITICALITY reject        TYPE S1ap-MME-UE-S1AP-ID                                PRESENCE mandatory } |
        { ID id-eNB-UE-S1AP-ID                        CRITICALITY reject        TYPE S1ap-ENB-UE-S1AP-ID                                PRESENCE mandatory } |
        { ID id-Routing-ID                                CRITICALITY reject        TYPE S1ap-Routing-ID                                        PRESENCE mandatory } |
        { ID id-LPPa-PDU                            CRITICALITY reject        TYPE S1ap-LPPa-PDU                                   PRESENCE mandatory } ,
        ...
}


-- **************************************************************
--
-- UPLINK UE ASSOCIATED LPPA TRANSPORT
--
-- **************************************************************


S1ap-UplinkUEAssociatedLPPaTransport ::= SEQUENCE {
    s1ap-UplinkUEAssociatedLPPaTransport-ies SEQUENCE (SIZE (0..s1ap-maxProtocolIEs)) OF S1ap-IE,
        ...
}


S1ap-UplinkUEAssociatedLPPaTransport-IEs S1AP-PROTOCOL-IES ::= {
        { ID id-MME-UE-S1AP-ID                        CRITICALITY reject        TYPE S1ap-MME-UE-S1AP-ID                                PRESENCE mandatory} |
        { ID id-eNB-UE-S1AP-ID                        CRITICALITY reject        TYPE S1ap-ENB-UE-S1AP-ID                                PRESENCE mandatory} |
        { ID id-Routing-ID                                CRITICALITY reject        TYPE S1ap-Routing-ID                                        PRESENCE mandatory} |
        { ID id-LPPa-PDU                            CRITICALITY reject        TYPE S1ap-LPPa-PDU                                   PRESENCE mandatory} ,
        ...
}


-- **************************************************************
--
-- DOWNLINK NON UE ASSOCIATED LPPA TRANSPORT
--
-- **************************************************************


S1ap-DownlinkNonUEAssociatedLPPaTransport ::= SEQUENCE {
    s1ap-DownlinkNonUEAssociatedLPPaTransport-ies SEQUENCE (SIZE (0..s1ap-maxProtocolIEs)) OF S1ap-IE,
        ...
}


S1ap-DownlinkNonUEAssociatedLPPaTransport-IEs S1AP-PROTOCOL-IES ::= {
        { ID id-Routing-ID                            CRITICALITY reject        TYPE S1ap-Routing-ID                                    PRESENCE mandatory} | 
        { ID id-LPPa-PDU                            CRITICALITY reject        TYPE S1ap-LPPa-PDU                                   PRESENCE mandatory} ,
        ...
}


-- **************************************************************
--
-- UPLINK NON UE ASSOCIATED LPPA TRANSPORT
--
-- **************************************************************


S1ap-UplinkNonUEAssociatedLPPaTransport ::= SEQUENCE {
    s1ap-UplinkNonUEAssociatedLPPaTransport-ies SEQUENCE (SIZE (0..s1ap-maxProtocolIEs)) OF S1ap-IE,
        ...
}


S1ap-UplinkNonUEAssociatedLPPaTransport-IEs S1AP-PROTOCOL-IES ::= {
        { ID id-Routing-ID                            CRITICALITY reject        TYPE S1ap-Routing-ID                                        PRESENCE mandatory} | 
        { ID id-LPPa-PDU                            CRITICALITY reject        TYPE S1ap-LPPa-PDU                                   PRESENCE mandatory} ,
        ...
}


END




-- **************************************************************
--
-- Information Element Definitions
--
-- **************************************************************


S1AP-IEs { 
itu-t (0) identified-organization (4) etsi (0) mobileDomain (0) 
eps-Access (21) modules (3) s1ap (1) version1 (1) s1ap-IEs (2) }


DEFINITIONS AUTOMATIC TAGS ::= 


BEGIN


IMPORTS
        S1ap-Presence
FROM S1AP-CommonDataTypes

        id-E-RABInformationListItem,
        id-E-RABItem,
        id-Bearers-SubjectToStatusTransfer-Item, 
        id-Time-Synchronization-Info,
        id-x2TNLConfigurationInfo,
        id-eNBX2ExtendedTransportLayerAddresses,
        id-MDTConfiguration,
        s1ap-maxNrOfCSGs,
        s1ap-maxNrOfE-RABs,
        s1ap-maxNrOfErrors,
        s1ap-maxnoofBPLMNs,
        s1ap-maxnoofPLMNsPerMME,
        s1ap-maxnoofTACs,
        s1ap-maxnoofEPLMNs,
        s1ap-maxnoofEPLMNsPlusOne,
        s1ap-maxnoofForbLACs,
        s1ap-maxnoofForbTACs,
        s1ap-maxnoofCells,
        s1ap-maxnoofCellID,
        s1ap-maxnoofEmergencyAreaID,
        s1ap-maxnoofTAIforWarning,
        s1ap-maxnoofCellinTAI,
        s1ap-maxnoofCellinEAI,
        s1ap-maxnoofeNBX2TLAs,
        s1ap-maxnoofeNBX2ExtTLAs,
        s1ap-maxnoofeNBX2GTPTLAs,
        s1ap-maxnoofRATs,
        s1ap-maxnoofGroupIDs,
        s1ap-maxnoofMMECs,
        s1ap-maxnoofTAforMDT,
        s1ap-maxnoofCellIDforMDT






FROM S1AP-Constants


        S1ap-Criticality,
        S1ap-ProcedureCode,
        S1ap-ProtocolIE-ID,
        S1ap-TriggeringMessage
FROM S1AP-CommonDataTypes


        ProtocolExtensionContainer{},
        S1AP-PROTOCOL-EXTENSION,
        ProtocolIE-SingleContainer{},
        S1AP-PROTOCOL-IES


FROM S1AP-Containers

        S1ap-IE

FROM S1AP-PDU;


-- A


S1ap-AreaScopeOfMDT ::= CHOICE {        
        cellBased                                        S1ap-CellBasedMDT,
        tABased                                                S1ap-TABasedMDT,
        pLMNWide                                        NULL,
        ...
}


S1ap-AllocationAndRetentionPriority ::= SEQUENCE {
        priorityLevel                                S1ap-PriorityLevel,
        pre-emptionCapability                S1ap-Pre-emptionCapability,
        pre-emptionVulnerability        S1ap-Pre-emptionVulnerability,
        iE-Extensions                                ProtocolExtensionContainer { {S1ap-AllocationAndRetentionPriority-ExtIEs} } OPTIONAL,
        ...
}


S1ap-AllocationAndRetentionPriority-ExtIEs S1AP-PROTOCOL-EXTENSION ::= {
        ...
}




-- B


S1ap-Bearers-SubjectToStatusTransfer-List ::= SEQUENCE (SIZE(1.. s1ap-maxNrOfE-RABs)) OF ProtocolIE-SingleContainer { { S1ap-Bearers-SubjectToStatusTransfer-ItemIEs } }


S1ap-Bearers-SubjectToStatusTransfer-ItemIEs S1AP-PROTOCOL-IES ::= {
        { ID id-Bearers-SubjectToStatusTransfer-Item        CRITICALITY ignore        TYPE S1ap-Bearers-SubjectToStatusTransfer-Item         PRESENCE mandatory        },
        ...
}


S1ap-Bearers-SubjectToStatusTransfer-Item ::= SEQUENCE {
        e-RAB-ID                                                                S1ap-E-RAB-ID,
        uL-S1ap-COUNTvalue                                                        S1ap-COUNTvalue,
        dL-S1ap-COUNTvalue                                                        S1ap-COUNTvalue,
        receiveStatusofULPDCPSDUs                                S1ap-ReceiveStatusofULPDCPSDUs                        OPTIONAL,
        iE-Extensions                                                        ProtocolExtensionContainer { {S1ap-Bearers-SubjectToStatusTransfer-ItemExtIEs} } OPTIONAL,
        ...
}


S1ap-Bearers-SubjectToStatusTransfer-ItemExtIEs S1AP-PROTOCOL-EXTENSION ::= {
        ...
}


S1ap-BitRate        ::= INTEGER (0..10000000000) 


S1ap-BPLMNs ::= SEQUENCE (SIZE(1.. s1ap-maxnoofBPLMNs)) OF S1ap-PLMNidentity


S1ap-BroadcastCancelledAreaList ::= CHOICE {
        cellID-Cancelled                                S1ap-CellID-Cancelled,
        tAI-Cancelled                                        S1ap-TAI-Cancelled,
        emergencyAreaID-Cancelled                S1ap-EmergencyAreaID-Cancelled,
        ...
}


S1ap-BroadcastCompletedAreaList ::= CHOICE {
        cellID-Broadcast                                S1ap-CellID-Broadcast,
        tAI-Broadcast                                        S1ap-TAI-Broadcast,
        emergencyAreaID-Broadcast                S1ap-EmergencyAreaID-Broadcast,
        ...
}




-- C


S1ap-CancelledCellinEAI ::= SEQUENCE (SIZE(1..s1ap-maxnoofCellinEAI)) OF S1ap-CancelledCellinEAI-Item


S1ap-CancelledCellinEAI-Item ::= SEQUENCE {
        eCGI                                        S1ap-EUTRAN-CGI,
        numberOfBroadcasts                S1ap-NumberOfBroadcasts,
        iE-Extensions                        ProtocolExtensionContainer { {S1ap-CancelledCellinEAI-Item-ExtIEs} } OPTIONAL,
        ...
}


S1ap-CancelledCellinEAI-Item-ExtIEs S1AP-PROTOCOL-EXTENSION ::= {
        ...
}


S1ap-CancelledCellinTAI ::= SEQUENCE (SIZE(1..s1ap-maxnoofCellinTAI)) OF S1ap-CancelledCellinTAI-Item


S1ap-CancelledCellinTAI-Item ::= SEQUENCE{
        eCGI                                S1ap-EUTRAN-CGI,
        numberOfBroadcasts        S1ap-NumberOfBroadcasts,
        iE-Extensions                ProtocolExtensionContainer { {S1ap-CancelledCellinTAI-Item-ExtIEs} } OPTIONAL,
        ...
}


S1ap-CancelledCellinTAI-Item-ExtIEs S1AP-PROTOCOL-EXTENSION ::= {
        ...
}


S1ap-Cause ::= CHOICE {
        radioNetwork                S1ap-CauseRadioNetwork,
        transport                        S1ap-CauseTransport,
        nas                                        S1ap-CauseNas,
        protocol                        S1ap-CauseProtocol,
        misc                                S1ap-CauseMisc,
        ...
}


S1ap-CauseMisc ::= ENUMERATED {
        control-processing-overload,
        not-enough-user-plane-processing-resources,
        hardware-failure,
        om-intervention,
        unspecified,
        unknown-PLMN,
...
}


S1ap-CauseProtocol ::= ENUMERATED {
        transfer-syntax-error,
        abstract-syntax-error-reject,
        abstract-syntax-error-ignore-and-notify,
        message-not-compatible-with-receiver-state,
        semantic-error,
        abstract-syntax-error-falsely-constructed-message,
        unspecified,
        ...
}


S1ap-CauseRadioNetwork ::= ENUMERATED {
        unspecified,
        tx2relocoverall-expiry,
        successful-handover,
        release-due-to-eutran-generated-reason,
        handover-cancelled,        
        partial-handover,        
        ho-failure-in-target-EPC-eNB-or-target-system,
        ho-target-not-allowed,
        tS1relocoverall-expiry,
        tS1relocprep-expiry,
        cell-not-available,
        unknown-targetID,
        no-radio-resources-available-in-target-cell,
        unknown-mme-ue-s1ap-id,
        unknown-enb-ue-s1ap-id,
        unknown-pair-ue-s1ap-id,
        handover-desirable-for-radio-reason,
        time-critical-handover,
        resource-optimisation-handover,
        reduce-load-in-serving-cell,
        user-inactivity,
        radio-connection-with-ue-lost,
        load-balancing-tau-required,
        cs-fallback-triggered,
        ue-not-available-for-ps-service,
        radio-resources-not-available,
        failure-in-radio-interface-procedure,
        invalid-qos-combination,
        interrat-redirection,
        interaction-with-other-procedure,
        unknown-S1ap-E-RAB-ID,
        multiple-S1ap-E-RAB-ID-instances,
        encryption-and-or-integrity-protection-algorithms-not-supported,
        s1-intra-system-handover-triggered,
        s1-inter-system-handover-triggered,
        x2-handover-triggered,
        ...,
        redirection-towards-1xRTT,
        not-supported-S1ap-QCI-value,
        invalid-CSG-Id


}


S1ap-CauseTransport ::= ENUMERATED {
        transport-resource-unavailable,
        unspecified,
        ...
}


S1ap-CauseNas ::= ENUMERATED {
        normal-release,
        authentication-failure,
        detach,
        unspecified,
        ...,
        csg-subscription-expiry
}


S1ap-CellAccessMode ::= ENUMERATED {
        hybrid, 
        ...
}


S1ap-CellIdentity                        ::= BIT STRING (SIZE (28))


S1ap-CellID-Broadcast ::= SEQUENCE (SIZE(1..s1ap-maxnoofCellID)) OF S1ap-CellID-Broadcast-Item


S1ap-CellID-Broadcast-Item ::= SEQUENCE {
        eCGI                                S1ap-EUTRAN-CGI,
        iE-Extensions                ProtocolExtensionContainer { {S1ap-CellID-Broadcast-Item-ExtIEs} } OPTIONAL,
        ...
}


S1ap-CellID-Broadcast-Item-ExtIEs S1AP-PROTOCOL-EXTENSION ::= {
        ...
}


S1ap-CellID-Cancelled::= SEQUENCE (SIZE(1..s1ap-maxnoofCellID)) OF S1ap-CellID-Cancelled-Item


S1ap-CellID-Cancelled-Item ::= SEQUENCE {
        eCGI                                S1ap-EUTRAN-CGI,
        numberOfBroadcasts        S1ap-NumberOfBroadcasts,
        iE-Extensions                ProtocolExtensionContainer { {S1ap-CellID-Cancelled-Item-ExtIEs} } OPTIONAL,
        ...
}


S1ap-CellID-Cancelled-Item-ExtIEs S1AP-PROTOCOL-EXTENSION ::= {
        ...
}


S1ap-CellBasedMDT::= SEQUENCE {
        cellIdListforMDT        S1ap-CellIdListforMDT,
        iE-Extensions                ProtocolExtensionContainer { {S1ap-CellBasedMDT-ExtIEs} } OPTIONAL,
        ...
}


S1ap-CellBasedMDT-ExtIEs S1AP-PROTOCOL-EXTENSION ::= {
        ...
}


S1ap-CellIdListforMDT ::= SEQUENCE (SIZE(1..s1ap-maxnoofCellIDforMDT)) OF S1ap-EUTRAN-CGI


S1ap-Cdma2000PDU        ::= OCTET STRING


S1ap-Cdma2000RATType ::= ENUMERATED {
        hRPD,
        onexRTT,
        ...
}


S1ap-Cdma2000SectorID ::= OCTET STRING


S1ap-Cdma2000HOStatus ::= ENUMERATED {
        hOSuccess,
        hOFailure,
        ...
}


S1ap-Cdma2000HORequiredIndication ::= ENUMERATED {
        true,
        ...
}


S1ap-Cdma2000OneXSRVCCInfo ::= SEQUENCE {
        cdma2000OneXMEID                        S1ap-Cdma2000OneXMEID,
        cdma2000OneXMSI                                S1ap-Cdma2000OneXMSI,
        cdma2000OneXPilot                        S1ap-Cdma2000OneXPilot,
        iE-Extensions                                ProtocolExtensionContainer { {S1ap-Cdma2000OneXSRVCCInfo-ExtIEs} } OPTIONAL,
        ...
}


S1ap-Cdma2000OneXSRVCCInfo-ExtIEs S1AP-PROTOCOL-EXTENSION ::= {
        ...
}


S1ap-Cdma2000OneXMEID ::= OCTET STRING


S1ap-Cdma2000OneXMSI ::= OCTET STRING


S1ap-Cdma2000OneXPilot ::= OCTET STRING


S1ap-Cdma2000OneXRAND ::= OCTET STRING




S1ap-Cell-Size ::= ENUMERATED {verysmall, small, medium, large, ...}


S1ap-CellType ::= SEQUENCE {
        cell-Size                                S1ap-Cell-Size,
        iE-Extensions                        ProtocolExtensionContainer { { S1ap-CellType-ExtIEs}}        OPTIONAL,
        ...
}


S1ap-CellType-ExtIEs S1AP-PROTOCOL-EXTENSION ::= {
        ...
}


S1ap-CGI ::= SEQUENCE {
        pLMNidentity                                S1ap-PLMNidentity,
        lAC                                S1ap-LAC,
        cI                                S1ap-CI,
        rAC                                S1ap-RAC                                                OPTIONAL,
        iE-Extensions        ProtocolExtensionContainer { {S1ap-CGI-ExtIEs} } OPTIONAL,
        ...
        }


S1ap-CGI-ExtIEs S1AP-PROTOCOL-EXTENSION ::= {
        ...
}


S1ap-CI                                        ::= OCTET STRING (SIZE (2))


S1ap-CNDomain ::= ENUMERATED {
        ps, 
        cs 
}


S1ap-ConcurrentWarningMessageIndicator ::= ENUMERATED {
        true
}


S1ap-Correlation-ID                ::= OCTET STRING (SIZE (4))


S1ap-CSFallbackIndicator ::= ENUMERATED { 
        cs-fallback-required,
        ...,
        cs-fallback-high-priority 
}


S1ap-CSG-Id                ::= BIT STRING (SIZE (27))




S1ap-CSG-IdList ::= SEQUENCE (SIZE (1..s1ap-maxNrOfCSGs)) OF S1ap-CSG-IdList-Item


S1ap-CSG-IdList-Item ::= SEQUENCE {
        cSG-Id                        S1ap-CSG-Id,
        iE-Extensions        ProtocolExtensionContainer { {S1ap-CSG-IdList-Item-ExtIEs} } OPTIONAL,
        ...
}


S1ap-CSG-IdList-Item-ExtIEs S1AP-PROTOCOL-EXTENSION ::= {
        ...
}


S1ap-CSGMembershipStatus ::= ENUMERATED { 
        member, 
        not-member
}




S1ap-COUNTvalue ::= SEQUENCE {
        pDCP-SN                        S1ap-PDCP-SN,
        hFN                                S1ap-HFN,
        iE-Extensions        ProtocolExtensionContainer { {S1ap-COUNTvalue-ExtIEs} } OPTIONAL,
        ...
}
S1ap-COUNTvalue-ExtIEs S1AP-PROTOCOL-EXTENSION ::= {
        ...
}


S1ap-CriticalityDiagnostics ::= SEQUENCE {
        procedureCode                                        S1ap-ProcedureCode                                        OPTIONAL,
        triggeringMessage                                S1ap-TriggeringMessage                                OPTIONAL,
        procedureCriticality                        S1ap-Criticality                                                OPTIONAL,
        iEsCriticalityDiagnostics                S1ap-CriticalityDiagnostics-IE-List         OPTIONAL,
        iE-Extensions                                        ProtocolExtensionContainer {{S1ap-CriticalityDiagnostics-ExtIEs}} OPTIONAL,
        ...
}


S1ap-CriticalityDiagnostics-ExtIEs S1AP-PROTOCOL-EXTENSION ::= {
        ...
}


S1ap-CriticalityDiagnostics-IE-List ::= SEQUENCE (SIZE (1..s1ap-maxNrOfErrors)) OF S1ap-CriticalityDiagnostics-IE-Item


S1ap-CriticalityDiagnostics-IE-Item ::=         SEQUENCE {
        iECriticality                        S1ap-Criticality,
        iE-ID                                        S1ap-ProtocolIE-ID,
        typeOfError                         S1ap-TypeOfError,
        iE-Extensions                        ProtocolExtensionContainer {{S1ap-CriticalityDiagnostics-IE-Item-ExtIEs}} OPTIONAL,
        ...
}


S1ap-CriticalityDiagnostics-IE-Item-ExtIEs S1AP-PROTOCOL-EXTENSION ::= {
        ...
}




-- D


S1ap-DataCodingScheme ::= BIT STRING (SIZE (8))


S1ap-DL-Forwarding ::= ENUMERATED {
        dL-Forwarding-proposed,
        ...
}


S1ap-Direct-Forwarding-Path-Availability ::= ENUMERATED {
        directPathAvailable,
        ...
}


S1ap-Data-Forwarding-Not-Possible ::= ENUMERATED {
        data-Forwarding-not-Possible,
        ...
}


-- E


S1ap-ECGIList ::= SEQUENCE (SIZE(1..s1ap-maxnoofCellID)) OF S1ap-EUTRAN-CGI


S1ap-EmergencyAreaIDList ::= SEQUENCE (SIZE(1..s1ap-maxnoofEmergencyAreaID)) OF S1ap-EmergencyAreaID


S1ap-EmergencyAreaID ::= OCTET STRING (SIZE (3))


S1ap-EmergencyAreaID-Broadcast ::= SEQUENCE (SIZE(1..s1ap-maxnoofEmergencyAreaID)) OF S1ap-EmergencyAreaID-Broadcast-Item


S1ap-EmergencyAreaID-Broadcast-Item ::= SEQUENCE {
        emergencyAreaID                        S1ap-EmergencyAreaID,
        completedCellinEAI                S1ap-CompletedCellinEAI,
        iE-Extensions                        ProtocolExtensionContainer { {S1ap-EmergencyAreaID-Broadcast-Item-ExtIEs} } OPTIONAL,
        ...
}


S1ap-EmergencyAreaID-Broadcast-Item-ExtIEs S1AP-PROTOCOL-EXTENSION ::= {
        ...
}


S1ap-EmergencyAreaID-Cancelled ::= SEQUENCE (SIZE(1..s1ap-maxnoofEmergencyAreaID)) OF S1ap-EmergencyAreaID-Cancelled-Item


S1ap-EmergencyAreaID-Cancelled-Item ::= SEQUENCE {
        emergencyAreaID                        S1ap-EmergencyAreaID,
        cancelledCellinEAI                S1ap-CancelledCellinEAI,
        iE-Extensions                        ProtocolExtensionContainer { {S1ap-EmergencyAreaID-Cancelled-Item-ExtIEs} } OPTIONAL,
        ...
}


S1ap-EmergencyAreaID-Cancelled-Item-ExtIEs S1AP-PROTOCOL-EXTENSION ::= {
        ...
}


S1ap-CompletedCellinEAI ::= SEQUENCE (SIZE(1..s1ap-maxnoofCellinEAI)) OF S1ap-CompletedCellinEAI-Item


S1ap-CompletedCellinEAI-Item ::= SEQUENCE {
        eCGI                                        S1ap-EUTRAN-CGI,
        iE-Extensions                        ProtocolExtensionContainer { {S1ap-CompletedCellinEAI-Item-ExtIEs} } OPTIONAL,
        ...
}


S1ap-CompletedCellinEAI-Item-ExtIEs S1AP-PROTOCOL-EXTENSION ::= {
        ...
}


S1ap-ENB-ID ::= CHOICE {
        macroENB-ID                        BIT STRING (SIZE(20)),
        homeENB-ID                        BIT STRING (SIZE(28)),
        ...
}


S1ap-GERAN-Cell-ID ::= SEQUENCE {
        lAI                                S1ap-LAI,
    rAC                                S1ap-RAC, 
        cI                                S1ap-CI,
        iE-Extensions                        ProtocolExtensionContainer { { S1ap-GERAN-Cell-ID-ExtIEs} } OPTIONAL,
        ...
}


S1ap-GERAN-Cell-ID-ExtIEs S1AP-PROTOCOL-EXTENSION ::= {
        ...
}


S1ap-Global-ENB-ID ::= SEQUENCE {
        pLMNidentity                        S1ap-PLMNidentity,
        eNB-ID                                        S1ap-ENB-ID,
        iE-Extensions                        ProtocolExtensionContainer { {S1ap-GlobalENB-ID-ExtIEs} } OPTIONAL,
        ...
}


S1ap-GlobalENB-ID-ExtIEs S1AP-PROTOCOL-EXTENSION ::= {
        ...
}


S1ap-GUMMEIList::= SEQUENCE (SIZE (1.. s1ap-maxnoofMMECs)) OF S1ap-GUMMEI


S1ap-ENB-StatusTransfer-TransparentContainer                ::= SEQUENCE {
        bearers-SubjectToStatusTransferList                S1ap-Bearers-SubjectToStatusTransfer-List,
        iE-Extensions                        ProtocolExtensionContainer { {S1ap-ENB-StatusTransfer-TransparentContainer-ExtIEs} } OPTIONAL,
        ...
}


S1ap-ENB-StatusTransfer-TransparentContainer-ExtIEs S1AP-PROTOCOL-EXTENSION ::= {
        ...
}


S1ap-ENB-UE-S1AP-ID                                ::= INTEGER (0..16777215)


S1ap-ENBname ::= PrintableString (SIZE (1..150,...))


S1ap-ENBX2TLAs ::= SEQUENCE (SIZE(1.. s1ap-maxnoofeNBX2TLAs)) OF S1ap-TransportLayerAddress


S1ap-EncryptionAlgorithms ::= BIT STRING (SIZE (16,...))


S1ap-EPLMNs ::= SEQUENCE (SIZE(1..s1ap-maxnoofEPLMNs)) OF S1ap-PLMNidentity
S1ap-EventType        ::= ENUMERATED {
        direct,
        change-of-serve-cell,
        stop-change-of-serve-cell,
        ...
}


S1ap-E-RAB-ID                ::= INTEGER (0..15, ...)


S1ap-E-RABInformationList        ::= SEQUENCE (SIZE (1.. s1ap-maxNrOfE-RABs)) OF ProtocolIE-SingleContainer { { S1ap-E-RABInformationListIEs } }


S1ap-E-RABInformationListIEs S1AP-PROTOCOL-IES ::= {
        { ID id-E-RABInformationListItem                        CRITICALITY ignore        TYPE S1ap-E-RABInformationListItem                        PRESENCE mandatory        },
        ...
}


S1ap-E-RABInformationListItem ::= SEQUENCE {
        e-RAB-ID                                                S1ap-E-RAB-ID,
        dL-Forwarding                                        S1ap-DL-Forwarding                OPTIONAL,
        iE-Extensions                                        ProtocolExtensionContainer { {S1ap-E-RABInformationListItem-ExtIEs} }                        OPTIONAL,
        ...
}


S1ap-E-RABInformationListItem-ExtIEs S1AP-PROTOCOL-EXTENSION ::= {
        ...
}


S1ap-E-RABList ::= SEQUENCE (SIZE(1.. s1ap-maxNrOfE-RABs)) OF ProtocolIE-SingleContainer { {S1ap-E-RABItemIEs} }


S1ap-E-RABItemIEs         S1AP-PROTOCOL-IES ::= {
        { ID id-E-RABItem         CRITICALITY ignore         TYPE S1ap-E-RABItem         PRESENCE mandatory },
        ...
}


S1ap-E-RABItem ::= SEQUENCE {
        e-RAB-ID                                        S1ap-E-RAB-ID,
        cause                                                S1ap-Cause,
        iE-Extensions                                ProtocolExtensionContainer { {S1ap-E-RABItem-ExtIEs} } OPTIONAL,
        ...
}


S1ap-E-RABItem-ExtIEs S1AP-PROTOCOL-EXTENSION ::= {
        ...
}




S1ap-E-RABLevelQoSParameters ::= SEQUENCE {
        qCI                        S1ap-QCI,
        allocationRetentionPriority                        S1ap-AllocationAndRetentionPriority,
        gbrQosInformation                                        S1ap-GBR-QosInformation                        OPTIONAL,
        iE-Extensions                                                ProtocolExtensionContainer { {S1ap-E-RABQoSParameters-ExtIEs} } OPTIONAL,
        ...
}


S1ap-E-RABQoSParameters-ExtIEs S1AP-PROTOCOL-EXTENSION ::= {
        ...
}




S1ap-EUTRAN-CGI ::= SEQUENCE {
        pLMNidentity                        S1ap-PLMNidentity,
        cell-ID                                        S1ap-CellIdentity,
        iE-Extensions                        ProtocolExtensionContainer { {S1ap-EUTRAN-CGI-ExtIEs} } OPTIONAL,
        ...
}


S1ap-EUTRAN-CGI-ExtIEs S1AP-PROTOCOL-EXTENSION ::= {
        ...
}


S1ap-EUTRANRoundTripDelayEstimationInfo ::= INTEGER (0..2047)


S1ap-ExtendedRNC-ID                                        ::= INTEGER (4096..65535)


S1ap-ExtendedRepetitionPeriod ::= INTEGER (4096..131071)


-- F


S1ap-ForbiddenInterRATs ::= ENUMERATED {
        all,
        geran,
        utran,
        cdma2000,
        ...,
        geranandutran,
        cdma2000andutran


}


S1ap-ForbiddenTAs ::= SEQUENCE (SIZE(1.. s1ap-maxnoofEPLMNsPlusOne)) OF S1ap-ForbiddenTAs-Item


S1ap-ForbiddenTAs-Item ::= SEQUENCE {
        pLMN-Identity                S1ap-PLMNidentity,
        forbiddenTACs                S1ap-ForbiddenTACs,
        iE-Extensions                ProtocolExtensionContainer { {S1ap-ForbiddenTAs-Item-ExtIEs} } OPTIONAL,
        ...
}


S1ap-ForbiddenTAs-Item-ExtIEs S1AP-PROTOCOL-EXTENSION ::= {
        ...
}


S1ap-ForbiddenTACs ::= SEQUENCE (SIZE(1..s1ap-maxnoofForbTACs)) OF S1ap-TAC


S1ap-ForbiddenLAs ::= SEQUENCE (SIZE(1..s1ap-maxnoofEPLMNsPlusOne)) OF S1ap-ForbiddenLAs-Item


S1ap-ForbiddenLAs-Item ::= SEQUENCE {
        pLMN-Identity                S1ap-PLMNidentity,
        forbiddenLACs                S1ap-ForbiddenLACs,
        iE-Extensions                ProtocolExtensionContainer { {S1ap-ForbiddenLAs-Item-ExtIEs} } OPTIONAL,
        ...
}


S1ap-ForbiddenLAs-Item-ExtIEs S1AP-PROTOCOL-EXTENSION ::= {
        ...
}


S1ap-ForbiddenLACs ::= SEQUENCE (SIZE(1..s1ap-maxnoofForbLACs)) OF S1ap-LAC


-- G


S1ap-GBR-QosInformation ::= SEQUENCE {
        e-RAB-MaximumBitrateDL                        S1ap-BitRate,
        e-RAB-MaximumBitrateUL                        S1ap-BitRate,
        e-RAB-GuaranteedBitrateDL                S1ap-BitRate,
        e-RAB-GuaranteedBitrateUL                S1ap-BitRate,
        iE-Extensions                                        ProtocolExtensionContainer { { S1ap-GBR-QosInformation-ExtIEs} } OPTIONAL,
        ...
}


S1ap-GBR-QosInformation-ExtIEs S1AP-PROTOCOL-EXTENSION ::= {
        ...
}




S1ap-GTP-TEID                                        ::= OCTET STRING (SIZE (4))


S1ap-GUMMEI                        ::= SEQUENCE {
        pLMN-Identity                S1ap-PLMNidentity,
        mME-Group-ID                S1ap-MME-Group-ID,
        mME-Code                        S1ap-MME-Code,
        iE-Extensions                ProtocolExtensionContainer { {S1ap-GUMMEI-ExtIEs} } OPTIONAL,
        ...
}


S1ap-GUMMEI-ExtIEs S1AP-PROTOCOL-EXTENSION ::= {
        ...
}


S1ap-GWContextReleaseIndication ::= ENUMERATED {
        true,
        ...
}


-- H


S1ap-HandoverRestrictionList ::= SEQUENCE {
        servingPLMN                                        S1ap-PLMNidentity,
        equivalentPLMNs                                S1ap-EPLMNs                                        OPTIONAL,
        forbiddenTAs                                S1ap-ForbiddenTAs                        OPTIONAL,
        forbiddenLAs                                S1ap-ForbiddenLAs                        OPTIONAL,
        forbiddenInterRATs                        S1ap-ForbiddenInterRATs                OPTIONAL, 
        iE-Extensions                                ProtocolExtensionContainer { {S1ap-HandoverRestrictionList-ExtIEs} }        OPTIONAL,
        ...
}


S1ap-HandoverRestrictionList-ExtIEs S1AP-PROTOCOL-EXTENSION ::= {
        ...
}


S1ap-HandoverType ::= ENUMERATED {
        intralte,
        ltetoutran,
        ltetogeran,
        utrantolte,
        gerantolte,
        ...
}


S1ap-HFN ::= INTEGER (0..1048575)


-- I


S1ap-ImmediateMDT ::= SEQUENCE { 
        measurementsToActivate                S1ap-MeasurementsToActivate,
        reportingTriggerMDT                        S1ap-ReportingTriggerMDT,
        thresholdeventA2                        S1ap-ThresholdEventA2                                OPTIONAL,
-- Included in case of event-triggered reporting for measurement M1
        periodicReportingMDT                S1ap-PeriodicReportingMDT                        OPTIONAL,
-- Included in case of periodic reporting
        iE-Extensions                                ProtocolExtensionContainer { { S1ap-ImmediateMDT-ExtIEs} } OPTIONAL,
        ...
}


S1ap-ImmediateMDT-ExtIEs S1AP-PROTOCOL-EXTENSION ::= {
        ...
}


S1ap-IMSI        ::=        OCTET STRING (SIZE (3..8))


S1ap-IntegrityProtectionAlgorithms ::= BIT STRING (SIZE (16,...))


S1ap-InterfacesToTrace ::= BIT STRING (SIZE (8))






-- J
-- K
-- L




S1ap-LAC        ::= OCTET STRING (SIZE (2))


S1ap-LAI ::= SEQUENCE {
        pLMNidentity                                S1ap-PLMNidentity,
        lAC                                S1ap-LAC,
        iE-Extensions                        ProtocolExtensionContainer { {S1ap-LAI-ExtIEs} } OPTIONAL,
        ...
}


S1ap-LAI-ExtIEs S1AP-PROTOCOL-EXTENSION ::= {
        ...
}


S1ap-LastVisitedCell-Item ::= CHOICE {
        e-UTRAN-Cell                                        S1ap-LastVisitedEUTRANCellInformation,
        uTRAN-Cell                                                S1ap-LastVisitedUTRANCellInformation,
        gERAN-Cell                                                S1ap-LastVisitedGERANCellInformation,
        ...
}
S1ap-LastVisitedEUTRANCellInformation ::= SEQUENCE {
        global-Cell-ID                                        S1ap-EUTRAN-CGI,
        cellType                                                S1ap-CellType,
        time-UE-StayedInCell                        S1ap-Time-UE-StayedInCell,
        iE-Extensions                                        ProtocolExtensionContainer { { S1ap-LastVisitedEUTRANCellInformation-ExtIEs} } OPTIONAL,
        ...
}
S1ap-LastVisitedEUTRANCellInformation-ExtIEs S1AP-PROTOCOL-EXTENSION ::= {
        ...
}
S1ap-LastVisitedUTRANCellInformation        ::= OCTET STRING


S1ap-LastVisitedGERANCellInformation ::= CHOICE {
        undefined                                                NULL,
        ...
}


S1ap-L3-Information                                ::= OCTET STRING
-- This is a dummy IE used only as a reference to the actual definition in relevant specification.


S1ap-LPPa-PDU ::=  OCTET STRING


S1ap-LoggedMDT ::= SEQUENCE {
        loggingInterval                                S1ap-LoggingInterval,
        loggingDuration                                S1ap-LoggingDuration,
        iE-Extensions                                ProtocolExtensionContainer { {S1ap-LoggedMDT-ExtIEs} } OPTIONAL,
        ...
}


S1ap-LoggedMDT-ExtIEs        S1AP-PROTOCOL-EXTENSION ::= {
...
}


S1ap-LoggingInterval ::= ENUMERATED {ms128, ms256, ms512, ms1024, ms2048, ms3072, ms4096, ms6144}


S1ap-LoggingDuration ::= ENUMERATED {m10, m20, m40, m60, m90, m120}


-- M


S1ap-MDT-Activation         ::= ENUMERATED { 
        immediate-MDT-only,
        immediate-MDT-and-Trace,
        logged-MDT-only,
        ...
}


S1ap-MDT-Configuration ::= SEQUENCE {
        mdt-Activation                                S1ap-MDT-Activation,
        areaScopeOfMDT                                S1ap-AreaScopeOfMDT,
        mDTMode                                                S1ap-MDTMode,
        iE-Extensions                                ProtocolExtensionContainer { { S1ap-MDT-Configuration-ExtIEs} } OPTIONAL,
        ...
}
S1ap-MDT-Configuration-ExtIEs S1AP-PROTOCOL-EXTENSION ::= {
        ...
}


S1ap-ManagementBasedMDTAllowed ::= ENUMERATED {allowed, ...}


S1ap-PrivacyIndicator ::= ENUMERATED {
        immediate-MDT,
        logged-MDT,
        ...
}


S1ap-MDTMode ::= CHOICE {
        immediateMDT                                S1ap-ImmediateMDT,
        loggedMDT                                        S1ap-LoggedMDT,
        ...
}


S1ap-MeasurementsToActivate ::= BIT STRING (SIZE (8))


S1ap-MeasurementThresholdA2 ::= CHOICE { 
        threshold-RSRP                                S1ap-Threshold-RSRP,
        threshold-RSRQ                                S1ap-Threshold-RSRQ,
        ...
}


S1ap-MessageIdentifier        ::= BIT STRING (SIZE (16))


S1ap-MMEname ::= PrintableString (SIZE (1..150,...))


S1ap-MMERelaySupportIndicator ::= ENUMERATED {true, ...}


S1ap-MME-Group-ID        ::= OCTET STRING (SIZE (2))


S1ap-MME-Code                ::= OCTET STRING (SIZE (1))


S1ap-MME-UE-S1AP-ID        ::= INTEGER (0..4294967295)
S1ap-M-TMSI                        ::= OCTET STRING (SIZE (4))


S1ap-MSClassmark2        ::= OCTET STRING
S1ap-MSClassmark3        ::= OCTET STRING


-- N


S1ap-NAS-PDU ::=  OCTET STRING


S1ap-NASSecurityParametersfromE-UTRAN ::= OCTET STRING


S1ap-NASSecurityParameterstoE-UTRAN ::= OCTET STRING


S1ap-NumberofBroadcastRequest ::= INTEGER (0..65535)


S1ap-NumberOfBroadcasts ::= INTEGER (0..65535)


-- O
S1ap-OldBSS-ToNewBSS-Information                ::= OCTET STRING
-- This is a dummy IE used only as a reference to the actual definition in relevant specification.


S1ap-OverloadAction ::= ENUMERATED {
        reject-non-emergency-mo-dt,
        reject-rrc-cr-signalling,
        permit-emergency-sessions-and-mobile-terminated-services-only,
        ...,
        permit-high-priority-sessions-and-mobile-terminated-services-only,
        reject-delay-tolerant-access
}


S1ap-OverloadResponse ::= CHOICE {
        overloadAction                                        S1ap-OverloadAction,
        ...
}




-- P


S1ap-PagingDRX ::= ENUMERATED {
        v32,
        v64,
        v128,
        v256,
        ...
        }


S1ap-PagingPriority ::= ENUMERATED {
        priolevel1,
        priolevel2,
        priolevel3,
        priolevel4,
        priolevel5,
        priolevel6,
        priolevel7,
        priolevel8,
        ...
}


S1ap-PDCP-SN ::= INTEGER (0..4095) 


S1ap-PeriodicReportingMDT ::= SEQUENCE { 
        reportInterval                                S1ap-ReportIntervalMDT,
        reportAmount                                S1ap-ReportAmountMDT,
        iE-Extensions                                ProtocolExtensionContainer { { S1ap-PeriodicReportingMDT-ExtIEs} } OPTIONAL,
        ...
}


S1ap-PeriodicReportingMDT-ExtIEs S1AP-PROTOCOL-EXTENSION ::= {
        ...
}


S1ap-PLMNidentity                                 ::= S1ap-TBCD-STRING 


S1ap-Pre-emptionCapability ::= ENUMERATED {
        shall-not-trigger-pre-emption,
        may-trigger-pre-emption
}


S1ap-Pre-emptionVulnerability ::= ENUMERATED {
        not-pre-emptable,
        pre-emptable
}


S1ap-PriorityLevel                                ::= INTEGER { spare (0), highest (1), lowest (14), no-priority (15) } (0..15)


S1ap-PS-ServiceNotAvailable ::= ENUMERATED {
        ps-service-not-available,
        ...
}


-- Q


S1ap-QCI                                                ::= INTEGER (0..255)


-- R


S1ap-ReceiveStatusofULPDCPSDUs ::= BIT STRING (SIZE(4096))


S1ap-RelativeMMECapacity                                ::= INTEGER (0..255)


S1ap-RelayNode-Indicator ::= ENUMERATED {
        true,
        ...
}


S1ap-RAC                                        ::= OCTET STRING (SIZE (1))


S1ap-ReportAmountMDT ::= ENUMERATED{r1, r2, r4, r8, r16, r32, r64, rinfinity}


S1ap-ReportIntervalMDT ::= ENUMERATED {ms120, ms240, ms480, ms640, ms1024, ms2048, ms5120, ms10240, min1, min6, min12, min30, min60} 


S1ap-ReportingTriggerMDT ::= ENUMERATED{
        periodic,
        a2eventtriggered,
        ...
}


S1ap-RequestType        ::= SEQUENCE {
        eventType                                 S1ap-EventType,
        reportArea                                 S1ap-ReportArea,
        iE-Extensions                        ProtocolExtensionContainer { { S1ap-RequestType-ExtIEs} }        OPTIONAL,
        ...
}




S1ap-RequestType-ExtIEs S1AP-PROTOCOL-EXTENSION ::= {
        ...
}


S1ap-RIMTransfer ::= SEQUENCE {
        rIMInformation                        S1ap-RIMInformation,
        rIMRoutingAddress                S1ap-RIMRoutingAddress                OPTIONAL,
        iE-Extensions                        ProtocolExtensionContainer { { S1ap-RIMTransfer-ExtIEs} }                        OPTIONAL,
        ...
}


S1ap-RIMTransfer-ExtIEs S1AP-PROTOCOL-EXTENSION ::= {
        ...
}


S1ap-RIMInformation ::= OCTET STRING


S1ap-RIMRoutingAddress ::= CHOICE {
        gERAN-Cell-ID                        S1ap-GERAN-Cell-ID,
        ...,
        targetRNC-ID                        S1ap-TargetRNC-ID
}


S1ap-ReportArea ::= ENUMERATED {
        ecgi,
        ...
}


S1ap-RepetitionPeriod ::= INTEGER (0..4095)




S1ap-RNC-ID                                        ::= INTEGER (0..4095)


S1ap-RRC-Container        ::= OCTET STRING


S1ap-RRC-Establishment-Cause ::= ENUMERATED {
        emergency,
        highPriorityAccess,
        mt-Access,
        mo-Signalling,
        mo-Data,
        ...,
        delay-TolerantAccess
}


S1ap-Routing-ID                ::= INTEGER (0..255)


-- S




S1ap-SecurityKey        ::= BIT STRING (SIZE(256))






S1ap-SecurityContext ::= SEQUENCE {
        nextHopChainingCount                INTEGER (0..7),
        nextHopParameter                        S1ap-SecurityKey,
        iE-Extensions                                ProtocolExtensionContainer { { S1ap-SecurityContext-ExtIEs} } OPTIONAL,
        ...
}




S1ap-SecurityContext-ExtIEs S1AP-PROTOCOL-EXTENSION ::= {
        ...
}


S1ap-SerialNumber ::= BIT STRING (SIZE (16))


S1ap-SONInformation ::= CHOICE{
        sONInformationRequest                S1ap-SONInformationRequest,
        sONInformationReply                        S1ap-SONInformationReply,
        ...
}


S1ap-SONInformationRequest ::= ENUMERATED { 
        x2TNL-Configuration-Info,
        ...,
        time-Synchronization-Info}


S1ap-SONInformationReply ::= SEQUENCE {
        x2TNLConfigurationInfo                        S1ap-X2TNLConfigurationInfo                        OPTIONAL,
        iE-Extensions                                        ProtocolExtensionContainer {{S1ap-SONInformationReply-ExtIEs}} OPTIONAL,
        ...
}


S1ap-SONInformationReply-ExtIEs S1AP-PROTOCOL-EXTENSION ::= {
-- Extension for Release 9 to transfer Time synchronization information --
        {ID id-Time-Synchronization-Info        CRITICALITY ignore                EXTENSION S1ap-TimeSynchronizationInfo                PRESENCE optional},
        ...
}




S1ap-SONConfigurationTransfer ::= SEQUENCE {
        targeteNB-ID                                        S1ap-TargeteNB-ID,
        sourceeNB-ID                                        S1ap-SourceeNB-ID,
        sONInformation                                        S1ap-SONInformation,
        iE-Extensions                        ProtocolExtensionContainer { { S1ap-SONConfigurationTransfer-ExtIEs} }                        OPTIONAL,
...
}


S1ap-SONConfigurationTransfer-ExtIEs S1AP-PROTOCOL-EXTENSION ::= {
-- Extension for Release 10 to transfer the IP addresses of the eNB initiating the ANR action --
        {ID id-x2TNLConfigurationInfo        CRITICALITY ignore        EXTENSION S1ap-X2TNLConfigurationInfo        PRESENCE conditional
        -- This IE shall be present if the SON Information IE contains the SON Information Request IE and the SON Information Request IE is set to X2TNL Configuration Info -- },
        ...
}






S1ap-Source-ToTarget-TransparentContainer ::= OCTET STRING
-- This IE includes a transparent container from the source RAN node to the target RAN node. 
-- The octets of the OCTET STRING are encoded according to the specifications of the target system.


S1ap-SourceBSS-ToTargetBSS-TransparentContainer                ::= OCTET STRING
-- This is a dummy IE used only as a reference to the actual definition in relevant specification.


S1ap-SourceeNB-ID ::= SEQUENCE {
        global-S1ap-ENB-ID        S1ap-Global-ENB-ID,
        selected-S1ap-TAI        S1ap-TAI,
        iE-Extensions        ProtocolExtensionContainer { {S1ap-SourceeNB-ID-ExtIEs} } OPTIONAL
}


S1ap-SourceeNB-ID-ExtIEs S1AP-PROTOCOL-EXTENSION ::= {
        ...
}


S1ap-SRVCCOperationPossible ::= ENUMERATED {
        possible,
        ...
}


S1ap-SRVCCHOIndication ::= ENUMERATED {
        pSandCS,
        cSonly,
        ...
}


S1ap-SourceeNB-ToTargeteNB-TransparentContainer                ::= SEQUENCE {
        rRC-Container                                        S1ap-RRC-Container,
        e-RABInformationList                        S1ap-E-RABInformationList                OPTIONAL,
        targetCell-ID                                        S1ap-EUTRAN-CGI,
        subscriberProfileIDforRFP                S1ap-SubscriberProfileIDforRFP                OPTIONAL,
        uE-HistoryInformation                        S1ap-UE-HistoryInformation,
        iE-Extensions                        ProtocolExtensionContainer { {S1ap-SourceeNB-ToTargeteNB-TransparentContainer-ExtIEs} } OPTIONAL,
        ...
}


S1ap-SourceeNB-ToTargeteNB-TransparentContainer-ExtIEs S1AP-PROTOCOL-EXTENSION ::= {
        ...
}




S1ap-SourceRNC-ToTargetRNC-TransparentContainer                ::= OCTET STRING
-- This is a dummy IE used only as a reference to the actual definition in relevant specification.




S1ap-ServedGUMMEIs ::= SEQUENCE (SIZE (1.. s1ap-maxnoofRATs)) OF S1ap-ServedGUMMEIsItem


S1ap-ServedGUMMEIsItem ::= SEQUENCE {
        servedPLMNs                                S1ap-ServedPLMNs,
        servedGroupIDs                        S1ap-ServedGroupIDs,
        servedMMECs                                S1ap-ServedMMECs,
        iE-Extensions                        ProtocolExtensionContainer { {S1ap-ServedGUMMEIsItem-ExtIEs} }        OPTIONAL,
        ...
}


S1ap-ServedGUMMEIsItem-ExtIEs S1AP-PROTOCOL-EXTENSION ::= {
        ...
}


S1ap-ServedGroupIDs ::= SEQUENCE (SIZE(1.. s1ap-maxnoofGroupIDs)) OF S1ap-MME-Group-ID
S1ap-ServedMMECs ::= SEQUENCE (SIZE(1.. s1ap-maxnoofMMECs)) OF S1ap-MME-Code


S1ap-ServedPLMNs ::= SEQUENCE (SIZE(1.. s1ap-maxnoofPLMNsPerMME)) OF S1ap-PLMNidentity


S1ap-SubscriberProfileIDforRFP ::= INTEGER (1..256) 


S1ap-SupportedTAs ::= SEQUENCE (SIZE(1.. s1ap-maxnoofTACs)) OF S1ap-SupportedTAs-Item


S1ap-SupportedTAs-Item ::=        SEQUENCE  {
        tAC                                        S1ap-TAC,
        broadcastPLMNs                S1ap-BPLMNs,
        iE-Extensions                ProtocolExtensionContainer { {S1ap-SupportedTAs-Item-ExtIEs} } OPTIONAL,
        ...
}


S1ap-SupportedTAs-Item-ExtIEs S1AP-PROTOCOL-EXTENSION ::= {
        ...
}


S1ap-StratumLevel ::= INTEGER (0..3, ...)


S1ap-SynchronizationStatus ::= ENUMERATED { synchronous, asynchronous, ... }


S1ap-TimeSynchronizationInfo ::= SEQUENCE {
        stratumLevel                                        S1ap-StratumLevel,
        synchronizationStatus                        S1ap-SynchronizationStatus,
        iE-Extensions                                        ProtocolExtensionContainer { { S1ap-TimeSynchronizationInfo-ExtIEs} } OPTIONAL,
        ...
}


S1ap-TimeSynchronizationInfo-ExtIEs S1AP-PROTOCOL-EXTENSION ::= {
        ...
}


S1ap-S-TMSI ::= SEQUENCE {
        mMEC        S1ap-MME-Code,
        m-TMSI        S1ap-M-TMSI,
        iE-Extensions                ProtocolExtensionContainer { {S1ap-S-TMSI-ExtIEs} } OPTIONAL,
        ...
}


S1ap-S-TMSI-ExtIEs S1AP-PROTOCOL-EXTENSION ::= {
        ...
}


-- T


S1ap-TAC ::= OCTET STRING (SIZE (2))


S1ap-TAIListforWarning ::= SEQUENCE (SIZE(1..s1ap-maxnoofTAIforWarning)) OF S1ap-TAI


S1ap-TAI ::= SEQUENCE {
        pLMNidentity                        S1ap-PLMNidentity,
        tAC                                                S1ap-TAC,
        iE-Extensions                        ProtocolExtensionContainer { {S1ap-TAI-ExtIEs} } OPTIONAL,
        ...
}


S1ap-TAI-ExtIEs S1AP-PROTOCOL-EXTENSION ::= {
        ...
}


S1ap-TAI-Broadcast ::= SEQUENCE (SIZE(1..s1ap-maxnoofTAIforWarning)) OF S1ap-TAI-Broadcast-Item


S1ap-TAI-Broadcast-Item ::= SEQUENCE {
        tAI                                        S1ap-TAI,
        completedCellinTAI        S1ap-CompletedCellinTAI,
        iE-Extensions                ProtocolExtensionContainer { {S1ap-TAI-Broadcast-Item-ExtIEs} } OPTIONAL,
        ...
}


S1ap-TAI-Broadcast-Item-ExtIEs S1AP-PROTOCOL-EXTENSION ::= {
        ...
}


S1ap-TAI-Cancelled ::= SEQUENCE (SIZE(1..s1ap-maxnoofTAIforWarning)) OF S1ap-TAI-Cancelled-Item


S1ap-TAI-Cancelled-Item ::= SEQUENCE {
        tAI                                        S1ap-TAI,
        cancelledCellinTAI        S1ap-CancelledCellinTAI,
        iE-Extensions                ProtocolExtensionContainer { {S1ap-TAI-Cancelled-Item-ExtIEs} } OPTIONAL,
        ...
}


S1ap-TAI-Cancelled-Item-ExtIEs S1AP-PROTOCOL-EXTENSION ::= {
        ...
}


S1ap-TABasedMDT ::= SEQUENCE {
        tAListforMDT                        S1ap-TAListforMDT,
        iE-Extensions                        ProtocolExtensionContainer { {S1ap-TABasedMDT-ExtIEs} } OPTIONAL,
        ...
}


S1ap-TABasedMDT-ExtIEs S1AP-PROTOCOL-EXTENSION ::= {
        ...
}


S1ap-TAListforMDT ::= SEQUENCE (SIZE(1..s1ap-maxnoofTAforMDT)) OF S1ap-TAC


S1ap-CompletedCellinTAI ::= SEQUENCE (SIZE(1..s1ap-maxnoofCellinTAI)) OF S1ap-CompletedCellinTAI-Item


S1ap-CompletedCellinTAI-Item ::= SEQUENCE{
        eCGI                                S1ap-EUTRAN-CGI,
        iE-Extensions                ProtocolExtensionContainer { {S1ap-CompletedCellinTAI-Item-ExtIEs} } OPTIONAL,
        ...
}


S1ap-CompletedCellinTAI-Item-ExtIEs S1AP-PROTOCOL-EXTENSION ::= {
        ...
}


S1ap-TBCD-STRING ::= OCTET STRING (SIZE (3))


S1ap-TargetID ::= CHOICE {
        targeteNB-ID                        S1ap-TargeteNB-ID,
        targetRNC-ID                        S1ap-TargetRNC-ID,
        cGI                                                S1ap-CGI,
        ...
}


S1ap-TargeteNB-ID ::= SEQUENCE {
        global-S1ap-ENB-ID        S1ap-Global-ENB-ID,
        selected-S1ap-TAI        S1ap-TAI,
        iE-Extensions        ProtocolExtensionContainer { {S1ap-TargeteNB-ID-ExtIEs} } OPTIONAL,
        ...
}


S1ap-TargeteNB-ID-ExtIEs S1AP-PROTOCOL-EXTENSION ::= {
        ...
}


S1ap-TargetRNC-ID ::= SEQUENCE {
        lAI                                        S1ap-LAI,
        rAC                                        S1ap-RAC                 OPTIONAL,
        rNC-ID                                S1ap-RNC-ID,
        extendedRNC-ID                S1ap-ExtendedRNC-ID                OPTIONAL,
        iE-Extensions                ProtocolExtensionContainer { {S1ap-TargetRNC-ID-ExtIEs} } OPTIONAL,
        ...
        }




S1ap-TargetRNC-ID-ExtIEs S1AP-PROTOCOL-EXTENSION ::= {
        ...
}




S1ap-TargeteNB-ToSourceeNB-TransparentContainer                ::= SEQUENCE {
        rRC-Container                        S1ap-RRC-Container,
        iE-Extensions                        ProtocolExtensionContainer { {S1ap-TargeteNB-ToSourceeNB-TransparentContainer-ExtIEs} } OPTIONAL,
        ...
}


S1ap-TargeteNB-ToSourceeNB-TransparentContainer-ExtIEs S1AP-PROTOCOL-EXTENSION ::= {
        ...
}


S1ap-Target-ToSource-TransparentContainer ::= OCTET STRING
-- This IE includes a transparent container from the target RAN node to the source RAN node. 
-- The octets of the OCTET STRING are coded according to the specifications of the target system.


S1ap-TargetRNC-ToSourceRNC-TransparentContainer                ::= OCTET STRING
-- This is a dummy IE used only as a reference to the actual definition in relevant specification.


S1ap-TargetBSS-ToSourceBSS-TransparentContainer                ::= OCTET STRING
-- This is a dummy IE used only as a reference to the actual definition in relevant specification.


S1ap-ThresholdEventA2 ::= SEQUENCE { 
        measurementThreshold                S1ap-MeasurementThresholdA2,
        iE-Extensions                                ProtocolExtensionContainer { { S1ap-ThresholdEventA2-ExtIEs} } OPTIONAL,
        ...
}


S1ap-ThresholdEventA2-ExtIEs S1AP-PROTOCOL-EXTENSION ::= {
        ...
}


S1ap-Threshold-RSRP ::= INTEGER(0..97)


S1ap-Threshold-RSRQ ::= INTEGER(0..34)


S1ap-TimeToWait ::= ENUMERATED {v1s, v2s, v5s, v10s, v20s, v60s, ...}


S1ap-Time-UE-StayedInCell ::= INTEGER (0..4095)


S1ap-TransportLayerAddress                ::= BIT STRING (SIZE(1..160, ...))


S1ap-TraceActivation ::= SEQUENCE {
        e-UTRAN-Trace-ID                                        S1ap-E-UTRAN-Trace-ID,
        interfacesToTrace                                S1ap-InterfacesToTrace,
     traceDepth                                                S1ap-TraceDepth,
     traceCollectionEntityIPAddress        S1ap-TransportLayerAddress,
        iE-Extensions                                        ProtocolExtensionContainer { { S1ap-TraceActivation-ExtIEs} }                OPTIONAL,
        ...
}


S1ap-TraceActivation-ExtIEs S1AP-PROTOCOL-EXTENSION ::= {
-- Extension for Rel-10 to support MDT --
        { ID id-MDTConfiguration        CRITICALITY ignore        EXTENSION S1ap-MDT-Configuration                PRESENCE        optional },
        ...
}


S1ap-TraceDepth ::= ENUMERATED { 
        minimum,
        medium,
        maximum,
        minimumWithoutVendorSpecificExtension,
        mediumWithoutVendorSpecificExtension,
        maximumWithoutVendorSpecificExtension,
        ...
}


S1ap-E-UTRAN-Trace-ID ::=  OCTET STRING (SIZE (8))


S1ap-TrafficLoadReductionIndication ::= INTEGER (1..99)


S1ap-TypeOfError ::= ENUMERATED {
        not-understood,
        missing,
        ...
}


-- U


S1ap-UEAggregateMaximumBitrate ::= SEQUENCE {
        uEaggregateMaximumBitRateDL                                S1ap-BitRate,
        uEaggregateMaximumBitRateUL                                S1ap-BitRate,
        iE-Extensions                                                        ProtocolExtensionContainer { {S1ap-UEAggregate-MaximumBitrates-ExtIEs} } OPTIONAL,
        ...
}


S1ap-UEAggregate-MaximumBitrates-ExtIEs S1AP-PROTOCOL-EXTENSION ::= {
        ...
}






S1ap-UE-S1AP-IDs ::= CHOICE{
        uE-S1AP-ID-pair                S1ap-UE-S1AP-ID-pair,
        mME-UE-S1AP-ID                S1ap-MME-UE-S1AP-ID,
        ...
}


S1ap-UE-S1AP-ID-pair ::= SEQUENCE{
        mME-UE-S1AP-ID                S1ap-MME-UE-S1AP-ID,
        eNB-UE-S1AP-ID                S1ap-ENB-UE-S1AP-ID,
        iE-Extensions                ProtocolExtensionContainer { {S1ap-UE-S1AP-ID-pair-ExtIEs} } OPTIONAL,
        ...
}
S1ap-UE-S1AP-ID-pair-ExtIEs S1AP-PROTOCOL-EXTENSION ::= {
        ...
}




S1ap-UE-associatedLogicalS1-ConnectionItem ::= SEQUENCE {
        mME-UE-S1AP-ID                                        S1ap-MME-UE-S1AP-ID OPTIONAL,
        eNB-UE-S1AP-ID                                        S1ap-ENB-UE-S1AP-ID OPTIONAL,
        iE-Extensions                                        ProtocolExtensionContainer { { S1ap-UE-associatedLogicalS1-ConnectionItemExtIEs} } OPTIONAL,
        ...
}




S1ap-UE-associatedLogicalS1-ConnectionItemExtIEs S1AP-PROTOCOL-EXTENSION ::= {
        ...
}


S1ap-UEIdentityIndexValue        ::=        BIT STRING (SIZE (10))


S1ap-UE-HistoryInformation ::= SEQUENCE (SIZE(1..s1ap-maxnoofCells)) OF S1ap-LastVisitedCell-Item


S1ap-UEPagingID ::= CHOICE {
        s-TMSI                S1ap-S-TMSI,
        iMSI                S1ap-IMSI,
        ...
        }


S1ap-UERadioCapability ::= OCTET STRING


S1ap-UESecurityCapabilities ::= SEQUENCE {
        encryptionAlgorithms                        S1ap-EncryptionAlgorithms,
        integrityProtectionAlgorithms        S1ap-IntegrityProtectionAlgorithms,
        iE-Extensions                                        ProtocolExtensionContainer { { S1ap-UESecurityCapabilities-ExtIEs} }                OPTIONAL,
...
}


S1ap-UESecurityCapabilities-ExtIEs S1AP-PROTOCOL-EXTENSION ::= {
        ...
}


-- V
-- W


S1ap-WarningAreaList ::= CHOICE {
        cellIDList                                                S1ap-ECGIList,
        trackingAreaListforWarning                S1ap-TAIListforWarning,
        emergencyAreaIDList                                S1ap-EmergencyAreaIDList,
        ...
}




S1ap-WarningType ::= OCTET STRING (SIZE (2))


S1ap-WarningSecurityInfo ::= OCTET STRING (SIZE (50))




S1ap-WarningMessageContents ::= OCTET STRING (SIZE(1..9600))




-- X




S1ap-X2TNLConfigurationInfo ::= SEQUENCE {
        eNBX2TransportLayerAddresses        S1ap-ENBX2TLAs,
        iE-Extensions                                        ProtocolExtensionContainer { { S1ap-X2TNLConfigurationInfo-ExtIEs} } OPTIONAL,
        ...
}


S1ap-X2TNLConfigurationInfo-ExtIEs S1AP-PROTOCOL-EXTENSION ::= {
-- Extension for Release 10 to transfer the IPsec and U-plane addresses during ANR action --
        {ID id-eNBX2ExtendedTransportLayerAddresses        CRITICALITY ignore        EXTENSION S1ap-ENBX2ExtTLAs        PRESENCE optional},
        ...
}


S1ap-ENBX2ExtTLAs ::= SEQUENCE (SIZE(1.. s1ap-maxnoofeNBX2ExtTLAs)) OF S1ap-ENBX2ExtTLA


S1ap-ENBX2ExtTLA ::= SEQUENCE {
        iPsecTLA                                        S1ap-TransportLayerAddress                OPTIONAL,
        gTPTLAa                                                S1ap-ENBX2GTPTLAs                                OPTIONAL,
        iE-Extensions                                ProtocolExtensionContainer { { S1ap-ENBX2ExtTLA-ExtIEs} } OPTIONAL,
        ...
}


S1ap-ENBX2ExtTLA-ExtIEs S1AP-PROTOCOL-EXTENSION ::= {
        ...
}


S1ap-ENBX2GTPTLAs ::= SEQUENCE (SIZE(1.. s1ap-maxnoofeNBX2GTPTLAs)) OF S1ap-TransportLayerAddress


-- Y
-- Z


END




-- **************************************************************
--
-- Common definitions
--
-- **************************************************************


S1AP-CommonDataTypes {
itu-t (0) identified-organization (4) etsi (0) mobileDomain (0) 
eps-Access (21) modules (3) s1ap (1) version1 (1) s1ap-CommonDataTypes (3) }


DEFINITIONS AUTOMATIC TAGS ::= 


BEGIN


S1ap-Criticality                ::= ENUMERATED { reject, ignore, notify }


S1ap-Presence                ::= ENUMERATED { optional, conditional, mandatory }


S1ap-PrivateIE-ID        ::= CHOICE {
        local                                INTEGER (0..65535),
        global                                OBJECT IDENTIFIER
}


S1ap-ProcedureCode                ::= INTEGER  {
        id-HandoverPreparation(0),
        id-HandoverResourceAllocation(1),
        id-HandoverNotification(2),
        id-PathSwitchRequest(3),
        id-HandoverCancel(4),
        id-E-RABSetup(5),
        id-E-RABModify(6),
        id-E-RABRelease(7),
        id-E-RABReleaseIndication(8),
        id-InitialContextSetup(9),
        id-Paging(10),
        id-downlinkNASTransport(11),
        id-initialUEMessage(12),
        id-uplinkNASTransport(13),
        id-Reset(14),
        id-ErrorIndication(15),
        id-NASNonDeliveryIndication(16),
        id-S1Setup(17),
        id-UEContextReleaseRequest(18),
        id-DownlinkS1cdma2000tunneling(19),
        id-UplinkS1cdma2000tunneling(20),
        id-UEContextModification(21),
        id-UECapabilityInfoIndication(22),
        id-UEContextRelease(23),
        id-eNBStatusTransfer(24),
        id-MMEStatusTransfer(25),
        id-DeactivateTrace(26),
        id-TraceStart(27),
        id-TraceFailureIndication(28),
        id-ENBConfigurationUpdate(29),
        id-MMEConfigurationUpdate(30),
        id-LocationReportingControl(31),
        id-LocationReportingFailureIndication(32),
        id-LocationReport(33),
        id-OverloadStart(34),
        id-OverloadStop(35),
        id-WriteReplaceWarning(36),
        id-eNBDirectInformationTransfer(37),
        id-MMEDirectInformationTransfer(38),
        id-PrivateMessage(39),
        id-eNBConfigurationTransfer(40),
        id-MMEConfigurationTransfer(41),
        id-CellTrafficTrace(42),
        id-Kill(43),
        id-downlinkUEAssociatedLPPaTransport(44),
        id-uplinkUEAssociatedLPPaTransport(45),
        id-downlinkNonUEAssociatedLPPaTransport(46),
        id-uplinkNonUEAssociatedLPPaTransport(47)
} (0..255)


S1ap-ProtocolExtensionID        ::= INTEGER (0..65535)


S1ap-ProtocolIE-ID                ::= INTEGER {
        id-MME-UE-S1AP-ID(0),
        id-HandoverType(1),
        id-Cause(2),
        id-SourceID(3),
        id-TargetID(4),
        id-eNB-UE-S1AP-ID(8),
        id-E-RABDataForwardingList(12),
        id-E-RABtoReleaseListHOCmd(13),
        id-E-RABDataForwardingItem(14),
        id-E-RABReleaseItemBearerRelComp(15),
        id-E-RABToBeSetupListBearerSUReq(16),
        id-E-RABToBeSetupItemBearerSUReq(17),
        id-E-RABAdmittedList(18),
        id-E-RABFailedToSetupListHOReqAck(19),
        id-E-RABAdmittedItem(20),
        id-E-RABFailedtoSetupItemHOReqAck(21),
        id-E-RABToBeSwitchedDLList(22),
        id-E-RABToBeSwitchedDLItem(23),
        id-E-RABToBeSetupListCtxtSUReq(24),
        id-TraceActivation(25),
        id-NAS-PDU(26),
        id-E-RABToBeSetupItemHOReq(27),
        id-E-RABSetupListBearerSURes(28),
        id-E-RABFailedToSetupListBearerSURes(29),
        id-E-RABToBeModifiedListBearerModReq(30),
        id-E-RABModifyListBearerModRes(31),
        id-E-RABFailedToModifyList(32),
        id-E-RABToBeReleasedList(33),
        id-E-RABFailedToReleaseList(34),
        id-E-RABItem(35),
        id-E-RABToBeModifiedItemBearerModReq(36),
        id-E-RABModifyItemBearerModRes(37),
        id-E-RABReleaseItem(38),
        id-E-RABSetupItemBearerSURes(39),
        id-SecurityContext(40),
        id-HandoverRestrictionList(41),
        id-UEPagingID(43),
        id-pagingDRX(44),
        id-TAIList(46),
        id-TAIItem(47),
        id-E-RABFailedToSetupListCtxtSURes(48),
        id-E-RABReleaseItemHOCmd(49),
        id-E-RABSetupItemCtxtSURes(50),
        id-E-RABSetupListCtxtSURes(51),
        id-E-RABToBeSetupItemCtxtSUReq(52),
        id-E-RABToBeSetupListHOReq(53),
        id-GERANtoLTEHOInformationRes(55),
        id-UTRANtoLTEHOInformationRes(57),
        id-CriticalityDiagnostics(58),
        id-Global-ENB-ID(59),
        id-eNBname(60),
        id-MMEname(61),
        id-ServedPLMNs(63),
        id-SupportedTAs(64),
        id-TimeToWait(65),
        id-uEaggregateMaximumBitrate(66),
        id-TAI(67),
        id-E-RABReleaseListBearerRelComp(69),
        id-cdma2000PDU(70),
        id-cdma2000RATType(71),
        id-cdma2000SectorID(72),
        id-SecurityKey(73),
        id-UERadioCapability(74),
        id-GUMMEI-ID(75),
        id-E-RABInformationListItem(78),
        id-Direct-Forwarding-Path-Availability(79),
        id-UEIdentityIndexValue(80),
        id-cdma2000HOStatus(83),
        id-cdma2000HORequiredIndication(84),
        id-E-UTRAN-Trace-ID(86),
        id-RelativeMMECapacity(87),
        id-SourceMME-UE-S1AP-ID(88),
        id-Bearers-SubjectToStatusTransfer-Item(89),
        id-eNB-StatusTransfer-TransparentContainer(90),
        id-UE-associatedLogicalS1-ConnectionItem(91),
        id-ResetType(92),
        id-UE-associatedLogicalS1-ConnectionListResAck(93),
        id-E-RABToBeSwitchedULItem(94),
        id-E-RABToBeSwitchedULList(95),
        id-S-TMSI(96),
        id-cdma2000OneXRAND(97),
        id-RequestType(98),
        id-UE-S1AP-IDs(99),
        id-EUTRAN-CGI(100),
        id-OverloadResponse(101),
        id-cdma2000OneXSRVCCInfo(102),
        id-E-RABFailedToBeReleasedList(103),
        id-Source-ToTarget-TransparentContainer(104),
        id-ServedGUMMEIs(105),
        id-SubscriberProfileIDforRFP(106),
        id-UESecurityCapabilities(107),
        id-CSFallbackIndicator(108),
        id-CNDomain(109),
        id-E-RABReleasedList(110),
        id-MessageIdentifier(111),
        id-SerialNumber(112),
        id-WarningAreaList(113),
        id-RepetitionPeriod(114),
        id-NumberofBroadcastRequest(115),
        id-WarningType(116),
        id-WarningSecurityInfo(117),
        id-DataCodingScheme(118),
        id-WarningMessageContents(119),
        id-BroadcastCompletedAreaList(120),
        id-Inter-SystemInformationTransferTypeEDT(121),
        id-Inter-SystemInformationTransferTypeMDT(122),
        id-Target-ToSource-TransparentContainer(123),
        id-SRVCCOperationPossible(124),
        id-SRVCCHOIndication(125),
        id-NAS-DownlinkCount(126),
        id-CSG-Id(127),
        id-CSG-IdList(128),
        id-SONConfigurationTransferECT(129),
        id-SONConfigurationTransferMCT(130),
        id-TraceCollectionEntityIPAddress(131),
        id-MSClassmark2(132),
        id-MSClassmark3(133),
        id-RRC-Establishment-Cause(134),
        id-NASSecurityParametersfromE-UTRAN(135),
        id-NASSecurityParameterstoE-UTRAN(136),
        id-DefaultPagingDRX(137),
        id-Source-ToTarget-TransparentContainer-Secondary(138),
        id-Target-ToSource-TransparentContainer-Secondary(139),
        id-EUTRANRoundTripDelayEstimationInfo(140),
        id-BroadcastCancelledAreaList(141),
        id-ConcurrentWarningMessageIndicator(142),
        id-Data-Forwarding-Not-Possible(143),
        id-ExtendedRepetitionPeriod(144),
        id-CellAccessMode(145),
        id-CSGMembershipStatus(146),
        id-LPPa-PDU(147),
        id-Routing-ID(148),
        id-Time-Synchronization-Info(149),
        id-PS-ServiceNotAvailable(150),
        id-PagingPriority(151),
        id-x2TNLConfigurationInfo(152),
        id-eNBX2ExtendedTransportLayerAddresses(153),
        id-GUMMEIList(154),
        id-GW-TransportLayerAddress(155),
        id-Correlation-ID(156),
        id-SourceMME-GUMMEI(157),
        id-MME-UE-S1AP-ID-2(158),
        id-RegisteredLAI(159),
        id-RelayNode-Indicator(160),
        id-TrafficLoadReductionIndication(161),
        id-MDTConfiguration(162),
        id-MMERelaySupportIndicator(163),
        id-GWContextReleaseIndication(164),
        id-ManagementBasedMDTAllowed(165),
        id-PrivacyIndicator(166)

} (0..65535)


S1ap-TriggeringMessage        ::= ENUMERATED { initiating-message, successful-outcome, unsuccessfull-outcome }


END


-- **************************************************************
--
-- Constant definitions
--
-- **************************************************************


S1AP-Constants { 
itu-t (0) identified-organization (4) etsi (0) mobileDomain (0) 
eps-Access (21) modules (3) s1ap (1) version1 (1) s1ap-Constants (4) } 


DEFINITIONS AUTOMATIC TAGS ::= 


BEGIN


-- **************************************************************
--
-- IE parameter types from other modules.
--
-- **************************************************************


IMPORTS
        S1ap-ProcedureCode,
        S1ap-ProtocolIE-ID


FROM S1AP-CommonDataTypes;




-- **************************************************************
--
-- Elementary Procedures
--
-- **************************************************************


id-HandoverPreparation                                 S1ap-ProcedureCode ::= 0
id-HandoverResourceAllocation                 S1ap-ProcedureCode ::= 1
id-HandoverNotification                         S1ap-ProcedureCode ::= 2
id-PathSwitchRequest                                 S1ap-ProcedureCode ::= 3
id-HandoverCancel                                         S1ap-ProcedureCode ::= 4
id-E-RABSetup                                                S1ap-ProcedureCode ::= 5
id-E-RABModify                                                 S1ap-ProcedureCode ::= 6
id-E-RABRelease                                                S1ap-ProcedureCode ::= 7
id-E-RABReleaseIndication                        S1ap-ProcedureCode ::= 8
id-InitialContextSetup                                S1ap-ProcedureCode ::= 9
id-Paging                                                        S1ap-ProcedureCode ::= 10
id-downlinkNASTransport                                S1ap-ProcedureCode ::= 11
id-initialUEMessage                                        S1ap-ProcedureCode ::= 12
id-uplinkNASTransport                                S1ap-ProcedureCode ::= 13
id-Reset                                                        S1ap-ProcedureCode::= 14
id-ErrorIndication                                        S1ap-ProcedureCode ::= 15
id-NASNonDeliveryIndication                        S1ap-ProcedureCode ::= 16
id-S1Setup                                                        S1ap-ProcedureCode ::= 17
id-UEContextReleaseRequest                        S1ap-ProcedureCode ::= 18
id-DownlinkS1cdma2000tunneling                S1ap-ProcedureCode ::= 19
id-UplinkS1cdma2000tunneling                S1ap-ProcedureCode ::= 20
id-UEContextModification                        S1ap-ProcedureCode ::= 21
id-UECapabilityInfoIndication                S1ap-ProcedureCode ::= 22
id-UEContextRelease                                        S1ap-ProcedureCode ::= 23
id-eNBStatusTransfer                                S1ap-ProcedureCode ::= 24
id-MMEStatusTransfer                                S1ap-ProcedureCode ::= 25
id-DeactivateTrace                                        S1ap-ProcedureCode ::= 26
id-TraceStart                                                S1ap-ProcedureCode ::= 27
id-TraceFailureIndication                        S1ap-ProcedureCode ::= 28
id-ENBConfigurationUpdate                        S1ap-ProcedureCode ::= 29
id-MMEConfigurationUpdate                        S1ap-ProcedureCode ::= 30
id-LocationReportingControl                        S1ap-ProcedureCode ::= 31
id-LocationReportingFailureIndication        S1ap-ProcedureCode ::= 32
id-LocationReport                                        S1ap-ProcedureCode ::= 33
id-OverloadStart                                        S1ap-ProcedureCode ::= 34
id-OverloadStop                                                S1ap-ProcedureCode ::= 35
id-WriteReplaceWarning                                S1ap-ProcedureCode ::= 36
id-eNBDirectInformationTransfer                S1ap-ProcedureCode ::= 37
id-MMEDirectInformationTransfer                S1ap-ProcedureCode ::= 38
id-PrivateMessage                                        S1ap-ProcedureCode ::= 39
id-eNBConfigurationTransfer                        S1ap-ProcedureCode ::= 40
id-MMEConfigurationTransfer                        S1ap-ProcedureCode ::= 41
id-CellTrafficTrace                                        S1ap-ProcedureCode ::= 42
id-Kill                                                                S1ap-ProcedureCode ::= 43
id-downlinkUEAssociatedLPPaTransport        S1ap-ProcedureCode ::= 44
id-uplinkUEAssociatedLPPaTransport                S1ap-ProcedureCode ::= 45
id-downlinkNonUEAssociatedLPPaTransport        S1ap-ProcedureCode ::= 46
id-uplinkNonUEAssociatedLPPaTransport        S1ap-ProcedureCode ::= 47


-- **************************************************************
--
-- Extension constants
--
-- **************************************************************


s1ap-maxPrivateIEs                                                 INTEGER ::= 65535
s1ap-maxProtocolExtensions                                 INTEGER ::= 65535
s1ap-maxProtocolIEs                                                INTEGER ::= 65535
-- **************************************************************
--
-- Lists
--
-- **************************************************************


s1ap-maxNrOfCSGs                                                                INTEGER ::= 256
s1ap-maxNrOfE-RABs                                                        INTEGER ::= 256
s1ap-maxnoofTAIs                                                                INTEGER ::= 256
s1ap-maxnoofTACs                                                                INTEGER ::= 256
s1ap-maxNrOfErrors                                                        INTEGER ::= 256
s1ap-maxnoofBPLMNs                                                        INTEGER ::= 6
s1ap-maxnoofPLMNsPerMME                                                INTEGER ::= 32
s1ap-maxnoofEPLMNs                                                        INTEGER ::= 15
s1ap-maxnoofEPLMNsPlusOne                                        INTEGER ::= 16
s1ap-maxnoofForbLACs                                                        INTEGER ::= 4096
s1ap-maxnoofForbTACs                                                        INTEGER ::= 4096
s1ap-maxNrOfIndividualS1ConnectionsToReset        INTEGER ::= 256
s1ap-maxnoofCells                                                        INTEGER ::= 16
s1ap-maxnoofTAIforWarning                                        INTEGER ::= 65535 
s1ap-maxnoofCellID                                                        INTEGER ::= 65535 
s1ap-maxnoofEmergencyAreaID                                        INTEGER ::= 65535 
s1ap-maxnoofCellinTAI                                                INTEGER ::= 65535 
s1ap-maxnoofCellinEAI                                                INTEGER ::= 65535 
s1ap-maxnoofeNBX2TLAs                                                INTEGER ::= 2
s1ap-maxnoofeNBX2ExtTLAs                                                INTEGER ::= 16
s1ap-maxnoofeNBX2GTPTLAs                                                INTEGER ::= 16
s1ap-maxnoofRATs                                                                INTEGER ::= 8
s1ap-maxnoofGroupIDs                                                        INTEGER ::= 65535
s1ap-maxnoofMMECs                                                        INTEGER ::= 256
s1ap-maxnoofCellIDforMDT                                                INTEGER ::= 32
s1ap-maxnoofTAforMDT                                                        INTEGER ::= 8




-- **************************************************************
--
-- IEs
--
-- **************************************************************


id-MME-UE-S1AP-ID                                                        S1ap-ProtocolIE-ID ::= 0
id-HandoverType                                                                S1ap-ProtocolIE-ID ::= 1
id-Cause                                                                        S1ap-ProtocolIE-ID ::= 2
id-SourceID                                                                        S1ap-ProtocolIE-ID ::= 3
id-TargetID                                                                        S1ap-ProtocolIE-ID ::= 4
id-eNB-UE-S1AP-ID                                                        S1ap-ProtocolIE-ID ::= 8
id-E-RABDataForwardingList                        S1ap-ProtocolIE-ID ::= 12
id-E-RABtoReleaseListHOCmd                                        S1ap-ProtocolIE-ID ::= 13
id-E-RABDataForwardingItem                                        S1ap-ProtocolIE-ID ::= 14
id-E-RABReleaseItemBearerRelComp                        S1ap-ProtocolIE-ID ::= 15
id-E-RABToBeSetupListBearerSUReq                        S1ap-ProtocolIE-ID ::= 16
id-E-RABToBeSetupItemBearerSUReq                        S1ap-ProtocolIE-ID ::= 17
id-E-RABAdmittedList                                                S1ap-ProtocolIE-ID ::= 18
id-E-RABFailedToSetupListHOReqAck                        S1ap-ProtocolIE-ID ::= 19
id-E-RABAdmittedItem                                                S1ap-ProtocolIE-ID ::= 20
id-E-RABFailedtoSetupItemHOReqAck                        S1ap-ProtocolIE-ID ::= 21
id-E-RABToBeSwitchedDLList                                        S1ap-ProtocolIE-ID ::= 22
id-E-RABToBeSwitchedDLItem                                        S1ap-ProtocolIE-ID ::= 23
id-E-RABToBeSetupListCtxtSUReq                                S1ap-ProtocolIE-ID ::= 24
id-TraceActivation                                                        S1ap-ProtocolIE-ID ::= 25
id-NAS-PDU                                                                        S1ap-ProtocolIE-ID ::= 26
id-E-RABToBeSetupItemHOReq                                        S1ap-ProtocolIE-ID ::= 27
id-E-RABSetupListBearerSURes                                S1ap-ProtocolIE-ID ::= 28
id-E-RABFailedToSetupListBearerSURes                S1ap-ProtocolIE-ID ::= 29
id-E-RABToBeModifiedListBearerModReq                S1ap-ProtocolIE-ID ::= 30
id-E-RABModifyListBearerModRes                                S1ap-ProtocolIE-ID ::= 31
id-E-RABFailedToModifyList                                        S1ap-ProtocolIE-ID ::= 32
id-E-RABToBeReleasedList                                        S1ap-ProtocolIE-ID ::= 33
id-E-RABFailedToReleaseList                                        S1ap-ProtocolIE-ID ::= 34
id-E-RABItem                                                                S1ap-ProtocolIE-ID ::= 35
id-E-RABToBeModifiedItemBearerModReq                S1ap-ProtocolIE-ID ::= 36
id-E-RABModifyItemBearerModRes                                S1ap-ProtocolIE-ID ::= 37
id-E-RABReleaseItem                                                        S1ap-ProtocolIE-ID ::= 38
id-E-RABSetupItemBearerSURes                                S1ap-ProtocolIE-ID ::= 39
id-SecurityContext                                                        S1ap-ProtocolIE-ID ::= 40
id-HandoverRestrictionList                                        S1ap-ProtocolIE-ID ::= 41
id-UEPagingID                                                                 S1ap-ProtocolIE-ID ::= 43
id-pagingDRX                                                                 S1ap-ProtocolIE-ID ::= 44
id-TAIList                                                                        S1ap-ProtocolIE-ID ::= 46
id-TAIItem                                                                        S1ap-ProtocolIE-ID ::= 47
id-E-RABFailedToSetupListCtxtSURes                        S1ap-ProtocolIE-ID ::= 48
id-E-RABReleaseItemHOCmd                                        S1ap-ProtocolIE-ID ::= 49
id-E-RABSetupItemCtxtSURes                                        S1ap-ProtocolIE-ID ::= 50
id-E-RABSetupListCtxtSURes                                        S1ap-ProtocolIE-ID ::= 51
id-E-RABToBeSetupItemCtxtSUReq                                S1ap-ProtocolIE-ID ::= 52
id-E-RABToBeSetupListHOReq                                        S1ap-ProtocolIE-ID ::= 53
id-GERANtoLTEHOInformationRes                                        S1ap-ProtocolIE-ID ::= 55
id-UTRANtoLTEHOInformationRes                                        S1ap-ProtocolIE-ID ::= 57
id-CriticalityDiagnostics                                                 S1ap-ProtocolIE-ID ::= 58
id-Global-ENB-ID                                                                S1ap-ProtocolIE-ID ::= 59
id-eNBname                                                                                S1ap-ProtocolIE-ID ::= 60
id-MMEname                                                                                S1ap-ProtocolIE-ID ::= 61
id-ServedPLMNs                                                                        S1ap-ProtocolIE-ID ::= 63
id-SupportedTAs                                                                        S1ap-ProtocolIE-ID ::= 64
id-TimeToWait                                                                        S1ap-ProtocolIE-ID ::= 65
id-uEaggregateMaximumBitrate                                        S1ap-ProtocolIE-ID ::= 66
id-TAI                                                                                        S1ap-ProtocolIE-ID ::= 67
id-E-RABReleaseListBearerRelComp                                S1ap-ProtocolIE-ID ::= 69
id-cdma2000PDU                                                                        S1ap-ProtocolIE-ID ::= 70
id-cdma2000RATType                                                                S1ap-ProtocolIE-ID ::= 71
id-cdma2000SectorID                                                                S1ap-ProtocolIE-ID ::= 72
id-SecurityKey                                                                        S1ap-ProtocolIE-ID ::= 73
id-UERadioCapability                                                        S1ap-ProtocolIE-ID ::= 74
id-GUMMEI-ID                                                                        S1ap-ProtocolIE-ID ::= 75
id-E-RABInformationListItem                                                S1ap-ProtocolIE-ID ::= 78
id-Direct-Forwarding-Path-Availability                        S1ap-ProtocolIE-ID ::= 79
id-UEIdentityIndexValue                                                        S1ap-ProtocolIE-ID ::= 80
id-cdma2000HOStatus                                                                S1ap-ProtocolIE-ID ::= 83
id-cdma2000HORequiredIndication                                        S1ap-ProtocolIE-ID ::= 84
id-E-UTRAN-Trace-ID                                                                S1ap-ProtocolIE-ID ::= 86
id-RelativeMMECapacity                                                        S1ap-ProtocolIE-ID ::= 87
id-SourceMME-UE-S1AP-ID                                                        S1ap-ProtocolIE-ID ::= 88
id-Bearers-SubjectToStatusTransfer-Item                        S1ap-ProtocolIE-ID ::= 89
id-eNB-StatusTransfer-TransparentContainer                S1ap-ProtocolIE-ID ::= 90
id-UE-associatedLogicalS1-ConnectionItem                S1ap-ProtocolIE-ID ::= 91
id-ResetType                                                                        S1ap-ProtocolIE-ID ::= 92
id-UE-associatedLogicalS1-ConnectionListResAck        S1ap-ProtocolIE-ID ::= 93
id-E-RABToBeSwitchedULItem                                                S1ap-ProtocolIE-ID ::= 94
id-E-RABToBeSwitchedULList                                                S1ap-ProtocolIE-ID ::= 95
id-S-TMSI                                                                                S1ap-ProtocolIE-ID ::= 96
id-cdma2000OneXRAND                                                                S1ap-ProtocolIE-ID ::= 97
id-RequestType                                                                        S1ap-ProtocolIE-ID ::= 98
id-UE-S1AP-IDs                                                                        S1ap-ProtocolIE-ID ::= 99
id-EUTRAN-CGI                                                                        S1ap-ProtocolIE-ID ::= 100
id-OverloadResponse                                                                S1ap-ProtocolIE-ID ::= 101
id-cdma2000OneXSRVCCInfo                                                S1ap-ProtocolIE-ID ::= 102
id-E-RABFailedToBeReleasedList                                        S1ap-ProtocolIE-ID ::= 103
id-Source-ToTarget-TransparentContainer                        S1ap-ProtocolIE-ID ::= 104
id-ServedGUMMEIs                                                                S1ap-ProtocolIE-ID ::= 105
id-SubscriberProfileIDforRFP                                        S1ap-ProtocolIE-ID ::= 106
id-UESecurityCapabilities                                                S1ap-ProtocolIE-ID ::= 107
id-CSFallbackIndicator                                                        S1ap-ProtocolIE-ID ::= 108
id-CNDomain                                                                                S1ap-ProtocolIE-ID ::= 109
id-E-RABReleasedList                                                        S1ap-ProtocolIE-ID ::= 110
id-MessageIdentifier                                                        S1ap-ProtocolIE-ID ::= 111
id-SerialNumber                                                                        S1ap-ProtocolIE-ID ::= 112
id-WarningAreaList                                                                S1ap-ProtocolIE-ID ::= 113
id-RepetitionPeriod                                                                S1ap-ProtocolIE-ID ::= 114
id-NumberofBroadcastRequest                                                S1ap-ProtocolIE-ID ::= 115
id-WarningType                                                                        S1ap-ProtocolIE-ID ::= 116
id-WarningSecurityInfo                                                        S1ap-ProtocolIE-ID ::= 117
id-DataCodingScheme                                                                S1ap-ProtocolIE-ID ::= 118
id-WarningMessageContents                                                S1ap-ProtocolIE-ID ::= 119
id-BroadcastCompletedAreaList                                        S1ap-ProtocolIE-ID ::= 120
id-Inter-SystemInformationTransferTypeEDT                S1ap-ProtocolIE-ID ::= 121
id-Inter-SystemInformationTransferTypeMDT                S1ap-ProtocolIE-ID ::= 122
id-Target-ToSource-TransparentContainer                        S1ap-ProtocolIE-ID ::= 123
id-SRVCCOperationPossible                                                S1ap-ProtocolIE-ID ::= 124
id-SRVCCHOIndication                                                        S1ap-ProtocolIE-ID ::= 125
id-NAS-DownlinkCount                                                        S1ap-ProtocolIE-ID ::= 126
id-CSG-Id                                                                                S1ap-ProtocolIE-ID ::= 127
id-CSG-IdList                                                                        S1ap-ProtocolIE-ID ::= 128
id-SONConfigurationTransferECT                                        S1ap-ProtocolIE-ID ::= 129
id-SONConfigurationTransferMCT                                        S1ap-ProtocolIE-ID ::= 130
id-TraceCollectionEntityIPAddress                                S1ap-ProtocolIE-ID ::= 131
id-MSClassmark2                                                                        S1ap-ProtocolIE-ID ::= 132
id-MSClassmark3                                                                        S1ap-ProtocolIE-ID ::= 133
id-RRC-Establishment-Cause                                                S1ap-ProtocolIE-ID ::= 134
id-NASSecurityParametersfromE-UTRAN                                S1ap-ProtocolIE-ID ::= 135
id-NASSecurityParameterstoE-UTRAN                                S1ap-ProtocolIE-ID ::= 136
id-DefaultPagingDRX                                                                S1ap-ProtocolIE-ID ::= 137
id-Source-ToTarget-TransparentContainer-Secondary        S1ap-ProtocolIE-ID ::= 138
id-Target-ToSource-TransparentContainer-Secondary        S1ap-ProtocolIE-ID ::= 139
id-EUTRANRoundTripDelayEstimationInfo                        S1ap-ProtocolIE-ID ::= 140
id-BroadcastCancelledAreaList                                        S1ap-ProtocolIE-ID ::= 141
id-ConcurrentWarningMessageIndicator                        S1ap-ProtocolIE-ID ::= 142
id-Data-Forwarding-Not-Possible                                        S1ap-ProtocolIE-ID ::= 143
id-ExtendedRepetitionPeriod                                                S1ap-ProtocolIE-ID ::= 144
id-CellAccessMode                                                                S1ap-ProtocolIE-ID ::= 145
id-CSGMembershipStatus                                                         S1ap-ProtocolIE-ID ::= 146
id-LPPa-PDU                                                                                S1ap-ProtocolIE-ID ::= 147
id-Routing-ID                                                                        S1ap-ProtocolIE-ID ::= 148
id-Time-Synchronization-Info                                        S1ap-ProtocolIE-ID ::= 149
id-PS-ServiceNotAvailable                                                S1ap-ProtocolIE-ID ::= 150
id-PagingPriority                                                                S1ap-ProtocolIE-ID ::= 151
id-x2TNLConfigurationInfo                                                S1ap-ProtocolIE-ID ::= 152
id-eNBX2ExtendedTransportLayerAddresses                        S1ap-ProtocolIE-ID ::= 153
id-GUMMEIList                                                                        S1ap-ProtocolIE-ID ::= 154
id-GW-TransportLayerAddress                                                S1ap-ProtocolIE-ID ::= 155
id-Correlation-ID                                                                S1ap-ProtocolIE-ID ::= 156
id-SourceMME-GUMMEI                                                                S1ap-ProtocolIE-ID ::= 157
id-MME-UE-S1AP-ID-2                                                                S1ap-ProtocolIE-ID ::= 158
id-RegisteredLAI                                                                S1ap-ProtocolIE-ID ::= 159
id-RelayNode-Indicator                                                        S1ap-ProtocolIE-ID ::= 160
id-TrafficLoadReductionIndication                                S1ap-ProtocolIE-ID ::= 161
id-MDTConfiguration                                                                S1ap-ProtocolIE-ID ::= 162
id-MMERelaySupportIndicator                                                S1ap-ProtocolIE-ID ::= 163
id-GWContextReleaseIndication                                        S1ap-ProtocolIE-ID ::= 164
id-ManagementBasedMDTAllowed                                        S1ap-ProtocolIE-ID ::= 165
id-PrivacyIndicator                                                                S1ap-ProtocolIE-ID ::= 166


END


-- **************************************************************
--
-- Container definitions
--
-- **************************************************************


S1AP-Containers {
itu-t (0) identified-organization (4) etsi (0) mobileDomain (0) 
eps-Access (21) modules (3) s1ap (1) version1 (1) s1ap-Containers (5) }


DEFINITIONS AUTOMATIC TAGS ::= 


BEGIN


-- **************************************************************
--
-- IE parameter types from other modules.
--
-- **************************************************************


IMPORTS
        S1ap-Criticality,
        S1ap-Presence,
        S1ap-PrivateIE-ID,
        S1ap-ProtocolExtensionID,
        S1ap-ProtocolIE-ID
FROM S1AP-CommonDataTypes


        s1ap-maxPrivateIEs,
        s1ap-maxProtocolExtensions,
        s1ap-maxProtocolIEs,
        s1ap-maxNrOfE-RABs
FROM S1AP-Constants;


-- **************************************************************
--
-- Class Definition for Protocol IEs
--
-- **************************************************************


S1AP-PROTOCOL-IES ::= CLASS {
        &id                                S1ap-ProtocolIE-ID                                         UNIQUE,
        &criticality                        S1ap-Criticality,
        &Value,
        &presence                        S1ap-Presence
}
WITH SYNTAX {
        ID                                &id
        CRITICALITY                        &criticality
        TYPE                                &Value
        PRESENCE                        &presence
}


-- **************************************************************
--
-- Class Definition for Protocol IEs
--
-- **************************************************************


S1AP-PROTOCOL-IES-PAIR ::= CLASS {
        &id                                S1ap-ProtocolIE-ID                                         UNIQUE,
        &firstCriticality                S1ap-Criticality,
        &FirstValue,
        &secondCriticality                S1ap-Criticality,
        &SecondValue,
        &presence                        S1ap-Presence
}
WITH SYNTAX {
        ID                                &id
        FIRST CRITICALITY                 &firstCriticality
        FIRST TYPE                        &FirstValue
        SECOND CRITICALITY                 &secondCriticality
        SECOND TYPE                        &SecondValue
        PRESENCE                        &presence
}


-- **************************************************************
--
-- Class Definition for Protocol Extensions
--
-- **************************************************************


S1AP-PROTOCOL-EXTENSION ::= CLASS {
        &id                                S1ap-ProtocolExtensionID                                 UNIQUE,
        &criticality                        S1ap-Criticality,
        &Extension,
        &presence                S1ap-Presence
}
WITH SYNTAX {
        ID                                &id
        CRITICALITY                        &criticality
        EXTENSION                        &Extension
        PRESENCE                &presence
}


-- **************************************************************
--
-- Class Definition for Private IEs
--
-- **************************************************************


S1AP-PRIVATE-IES ::= CLASS {
        &id                                S1ap-PrivateIE-ID,
        &criticality                        S1ap-Criticality,
        &Value,
        &presence                S1ap-Presence
}
WITH SYNTAX {
        ID                                &id
        CRITICALITY                        &criticality
        TYPE                        &Value
        PRESENCE                &presence
}


-- **************************************************************
--
-- Container for Protocol IEs
--
-- **************************************************************


ProtocolIE-Container {S1AP-PROTOCOL-IES : IEsSetParam} ::= 
        SEQUENCE (SIZE (0..s1ap-maxProtocolIEs)) OF
        ProtocolIE-Field {{IEsSetParam}}


ProtocolIE-SingleContainer {S1AP-PROTOCOL-IES : IEsSetParam} ::= 
        ProtocolIE-Field {{IEsSetParam}}


ProtocolIE-Field {S1AP-PROTOCOL-IES : IEsSetParam} ::= SEQUENCE {
        id                                S1AP-PROTOCOL-IES.&id                                ({IEsSetParam}),
        criticality                        S1AP-PROTOCOL-IES.&criticality                        ({IEsSetParam}{@id}),
        value                                S1AP-PROTOCOL-IES.&Value                        ({IEsSetParam}{@id})
}


-- **************************************************************
--
-- Container for Protocol IE Pairs
--
-- **************************************************************


ProtocolIE-ContainerPair {S1AP-PROTOCOL-IES-PAIR : IEsSetParam} ::= 
        SEQUENCE (SIZE (0..s1ap-maxProtocolIEs)) OF
        ProtocolIE-FieldPair {{IEsSetParam}}


ProtocolIE-FieldPair {S1AP-PROTOCOL-IES-PAIR : IEsSetParam} ::= SEQUENCE {
        id                                S1AP-PROTOCOL-IES-PAIR.&id                        ({IEsSetParam}),
        firstCriticality                S1AP-PROTOCOL-IES-PAIR.&firstCriticality        ({IEsSetParam}{@id}),
        firstValue                        S1AP-PROTOCOL-IES-PAIR.&FirstValue                ({IEsSetParam}{@id}),
        secondCriticality                S1AP-PROTOCOL-IES-PAIR.&secondCriticality        ({IEsSetParam}{@id}),
        secondValue                        S1AP-PROTOCOL-IES-PAIR.&SecondValue                ({IEsSetParam}{@id})
}


-- **************************************************************
--
-- Container Lists for Protocol IE Containers
--
-- **************************************************************


ProtocolIE-ContainerList {INTEGER : lowerBound, INTEGER : upperBound, S1AP-PROTOCOL-IES : IEsSetParam} ::=
        SEQUENCE (SIZE (lowerBound..upperBound)) OF
        ProtocolIE-SingleContainer {{IEsSetParam}}


ProtocolIE-ContainerPairList {INTEGER : lowerBound, INTEGER : upperBound, S1AP-PROTOCOL-IES-PAIR : IEsSetParam} ::=
        SEQUENCE (SIZE (lowerBound..upperBound)) OF
        ProtocolIE-ContainerPair {{IEsSetParam}}


-- **************************************************************
--
-- Container for Protocol Extensions
--
-- **************************************************************


ProtocolExtensionContainer {S1AP-PROTOCOL-EXTENSION : ExtensionSetParam} ::= 
        SEQUENCE (SIZE (1..s1ap-maxProtocolExtensions)) OF
        ProtocolExtensionField {{ExtensionSetParam}}


ProtocolExtensionField {S1AP-PROTOCOL-EXTENSION : ExtensionSetParam} ::= SEQUENCE {
        id                                S1AP-PROTOCOL-EXTENSION.&id                        ({ExtensionSetParam}),
        criticality                        S1AP-PROTOCOL-EXTENSION.&criticality                ({ExtensionSetParam}{@id}),
        extensionValue                        S1AP-PROTOCOL-EXTENSION.&Extension                ({ExtensionSetParam}{@id})
}


-- **************************************************************
--
-- Container for Private IEs
--
-- **************************************************************


PrivateIE-Container {S1AP-PRIVATE-IES : IEsSetParam } ::= 
        SEQUENCE (SIZE (1.. s1ap-maxPrivateIEs)) OF
        PrivateIE-Field {{IEsSetParam}}


PrivateIE-Field {S1AP-PRIVATE-IES : IEsSetParam} ::= SEQUENCE {
        id                                S1AP-PRIVATE-IES.&id                        ({IEsSetParam}),
        criticality                        S1AP-PRIVATE-IES.&criticality                ({IEsSetParam}{@id}),
        value                        S1AP-PRIVATE-IES.&Value                ({IEsSetParam}{@id})
}


END


-- **************************************************************
--
-- for S1ap-IE
--
-- **************************************************************

S1AP-PDU {
    itu-t (0) identified-organization (4) etsi (0) mobileDomain (0)
    eps-Access (21) modules (3) s1ap (1) version1 (1)
}

DEFINITIONS AUTOMATIC TAGS ::=

BEGIN

IMPORTS
    S1ap-Criticality,
    S1ap-ProtocolIE-ID

FROM S1AP-CommonDataTypes;

S1ap-IE ::= SEQUENCE {
    id          S1ap-ProtocolIE-ID,
    criticality S1ap-Criticality,
    value       ANY
}

END
