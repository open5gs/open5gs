NRPPA-PDU-Descriptions {
itu-t (0) identified-organization (4) etsi (0) mobileDomain (0)
ngran-access (22) modules (3) nrppa (4) version1 (1) nrppa-PDU-Descriptions (0) }

DEFINITIONS AUTOMATIC TAGS ::=

BEGIN

-- **************************************************************
--
-- IE parameter types from other modules.
--
-- **************************************************************

IMPORTS
    Criticality,
    ProcedureCode,
    NRPPATransactionID

FROM NRPPA-CommonDataTypes


    ErrorIndication,
    PrivateMessage,
    E-CIDMeasurementInitiationRequest,
    E-CIDMeasurementInitiationResponse,
    E-CIDMeasurementInitiationFailure,
    E-CIDMeasurementFailureIndication,
    E-CIDMeasurementReport,
    E-CIDMeasurementTerminationCommand,
    OTDOAInformationRequest,
    OTDOAInformationResponse,
    OTDOAInformationFailure,
    AssistanceInformationControl,
    AssistanceInformationFeedback,
    PositioningInformationRequest,
    PositioningInformationResponse,
    PositioningInformationFailure,
    PositioningInformationUpdate,
    MeasurementRequest,
    MeasurementResponse,
    MeasurementFailure,
    MeasurementReport,
    MeasurementUpdate,
    MeasurementAbort,
    MeasurementFailureIndication,
    TRPInformationRequest,
    TRPInformationResponse,
    TRPInformationFailure,
    PositioningActivationRequest,
    PositioningActivationResponse,
    PositioningActivationFailure,
    PositioningDeactivation,




    PRSConfigurationRequest,
    PRSConfigurationResponse,
    PRSConfigurationFailure,
    MeasurementPreconfigurationRequired,
    MeasurementPreconfigurationConfirm,
    MeasurementPreconfigurationRefuse,
    MeasurementActivation


FROM NRPPA-PDU-Contents

    id-errorIndication,
    id-privateMessage,
    id-e-CIDMeasurementInitiation,
    id-e-CIDMeasurementFailureIndication,
    id-e-CIDMeasurementReport,
    id-e-CIDMeasurementTermination,
    id-oTDOAInformationExchange,
    id-assistanceInformationControl,
    id-assistanceInformationFeedback,
    id-positioningInformationExchange,
    id-positioningInformationUpdate,
    id-Measurement,
    id-MeasurementReport,
    id-MeasurementUpdate,
    id-MeasurementAbort,
    id-MeasurementFailureIndication,
    id-tRPInformationExchange,
    id-positioningActivation,
    id-positioningDeactivation,
    id-pRSConfigurationExchange,
    id-measurementPreconfiguration,
    id-measurementActivation



FROM NRPPA-Constants;

-- **************************************************************
--
-- Interface Elementary Procedure Class
--
-- **************************************************************

NRPPA-ELEMENTARY-PROCEDURE ::= CLASS {
    &InitiatingMessage              ,
    &SuccessfulOutcome                          OPTIONAL,
    &UnsuccessfulOutcome                        OPTIONAL,
    &procedureCode              ProcedureCode   UNIQUE,
    &criticality                Criticality DEFAULT ignore
}
WITH SYNTAX {
    INITIATING MESSAGE          &InitiatingMessage
    [SUCCESSFUL OUTCOME     &SuccessfulOutcome]




    [UNSUCCESSFUL OUTCOME         &UnsuccessfulOutcome]
    PROCEDURE CODE                &procedureCode
    [CRITICALITY                  &criticality]
}

-- **************************************************************
--
-- Interface PDU Definition
--
-- **************************************************************

NRPPA-PDU ::= CHOICE {
    initiatingMessage       InitiatingMessage,
    successfulOutcome       SuccessfulOutcome,
    unsuccessfulOutcome UnsuccessfulOutcome,
    ...
}

InitiatingMessage ::= SEQUENCE {
    procedureCode           NRPPA-ELEMENTARY-PROCEDURE.&procedureCode       ({NRPPA-ELEMENTARY-PROCEDURES}),
    criticality         NRPPA-ELEMENTARY-PROCEDURE.&criticality         ({NRPPA-ELEMENTARY-PROCEDURES}{@procedureCode}),
    nrppatransactionID      NRPPATransactionID,
    value                   NRPPA-ELEMENTARY-PROCEDURE.&InitiatingMessage   ({NRPPA-ELEMENTARY-PROCEDURES}{@procedureCode})
}

SuccessfulOutcome ::= SEQUENCE {
    procedureCode           NRPPA-ELEMENTARY-PROCEDURE.&procedureCode       ({NRPPA-ELEMENTARY-PROCEDURES}),
    criticality         NRPPA-ELEMENTARY-PROCEDURE.&criticality         ({NRPPA-ELEMENTARY-PROCEDURES}{@procedureCode}),
    nrppatransactionID      NRPPATransactionID,
    value                   NRPPA-ELEMENTARY-PROCEDURE.&SuccessfulOutcome   ({NRPPA-ELEMENTARY-PROCEDURES}{@procedureCode})
}

UnsuccessfulOutcome ::= SEQUENCE {
    procedureCode           NRPPA-ELEMENTARY-PROCEDURE.&procedureCode       ({NRPPA-ELEMENTARY-PROCEDURES}),
    criticality         NRPPA-ELEMENTARY-PROCEDURE.&criticality         ({NRPPA-ELEMENTARY-PROCEDURES}{@procedureCode}),
    nrppatransactionID      NRPPATransactionID,
    value                   NRPPA-ELEMENTARY-PROCEDURE.&UnsuccessfulOutcome ({NRPPA-ELEMENTARY-PROCEDURES}{@procedureCode})
}


-- **************************************************************
--
-- Interface Elementary Procedure List
--
-- **************************************************************

NRPPA-ELEMENTARY-PROCEDURES NRPPA-ELEMENTARY-PROCEDURE ::= {
    NRPPA-ELEMENTARY-PROCEDURES-CLASS-1         |
    NRPPA-ELEMENTARY-PROCEDURES-CLASS-2         ,
    ...
}

NRPPA-ELEMENTARY-PROCEDURES-CLASS-1 NRPPA-ELEMENTARY-PROCEDURE ::= {
    e-CIDMeasurementInitiation |




    oTDOAInformationExchange    |
    positioningInformationExchange    |
    measurement                       |
    tRPInformationExchange      |
    positioningActivation       |
    pRSConfigurationExchange    |
    measurementPreconfiguration,

    ...
}

NRPPA-ELEMENTARY-PROCEDURES-CLASS-2 NRPPA-ELEMENTARY-PROCEDURE ::= {
    e-CIDMeasurementFailureIndication       |
    e-CIDMeasurementReport                  |
    e-CIDMeasurementTermination             |
    errorIndication                         |
    privateMessage                          |
    assistanceInformationControl            |
    assistanceInformationFeedback           |
    positioningInformationUpdate            |
    measurementReport                       |
    measurementUpdate                       |
    measurementAbort                        |
    measurementFailureIndication        |
    positioningDeactivation     |
    measurementActivation,
    ...
}


-- **************************************************************
--
-- Interface Elementary Procedures
--
-- **************************************************************

e-CIDMeasurementInitiation NRPPA-ELEMENTARY-PROCEDURE ::= {
    INITIATING MESSAGE      E-CIDMeasurementInitiationRequest
    SUCCESSFUL OUTCOME      E-CIDMeasurementInitiationResponse
    UNSUCCESSFUL OUTCOME    E-CIDMeasurementInitiationFailure
    PROCEDURE CODE          id-e-CIDMeasurementInitiation
    CRITICALITY             reject
}

e-CIDMeasurementFailureIndication NRPPA-ELEMENTARY-PROCEDURE ::= {
    INITIATING MESSAGE      E-CIDMeasurementFailureIndication
    PROCEDURE CODE          id-e-CIDMeasurementFailureIndication
    CRITICALITY             ignore
}

e-CIDMeasurementReport NRPPA-ELEMENTARY-PROCEDURE ::= {
    INITIATING MESSAGE      E-CIDMeasurementReport
    PROCEDURE CODE          id-e-CIDMeasurementReport
    CRITICALITY             ignore




}

e-CIDMeasurementTermination NRPPA-ELEMENTARY-PROCEDURE ::= {
    INITIATING MESSAGE      E-CIDMeasurementTerminationCommand
    PROCEDURE CODE          id-e-CIDMeasurementTermination
    CRITICALITY             reject
}

oTDOAInformationExchange NRPPA-ELEMENTARY-PROCEDURE ::= {
    INITIATING MESSAGE      OTDOAInformationRequest
    SUCCESSFUL OUTCOME      OTDOAInformationResponse
    UNSUCCESSFUL OUTCOME    OTDOAInformationFailure
    PROCEDURE CODE          id-oTDOAInformationExchange
    CRITICALITY             reject
}


assistanceInformationControl NRPPA-ELEMENTARY-PROCEDURE ::= {
    INITIATING MESSAGE      AssistanceInformationControl
    PROCEDURE CODE          id-assistanceInformationControl
    CRITICALITY             reject
}

assistanceInformationFeedback NRPPA-ELEMENTARY-PROCEDURE ::= {
    INITIATING MESSAGE      AssistanceInformationFeedback
    PROCEDURE CODE          id-assistanceInformationFeedback
    CRITICALITY             reject
}


errorIndication NRPPA-ELEMENTARY-PROCEDURE ::= {
    INITIATING MESSAGE      ErrorIndication
    PROCEDURE CODE          id-errorIndication
    CRITICALITY         ignore
}


privateMessage           NRPPA-ELEMENTARY-PROCEDURE ::= {
    INITIATING MESSAGE       PrivateMessage
    PROCEDURE CODE           id-privateMessage
    CRITICALITY          ignore
}


positioningInformationExchange NRPPA-ELEMENTARY-PROCEDURE ::= {
    INITIATING MESSAGE      PositioningInformationRequest
    SUCCESSFUL OUTCOME      PositioningInformationResponse
    UNSUCCESSFUL OUTCOME    PositioningInformationFailure
    PROCEDURE CODE          id-positioningInformationExchange
    CRITICALITY             reject
}

positioningInformationUpdate    NRPPA-ELEMENTARY-PROCEDURE ::= {
    INITIATING MESSAGE      PositioningInformationUpdate




    PROCEDURE CODE           id-positioningInformationUpdate
    CRITICALITY              ignore
}

measurement NRPPA-ELEMENTARY-PROCEDURE ::= {
    INITIATING MESSAGE      MeasurementRequest
    SUCCESSFUL OUTCOME      MeasurementResponse
    UNSUCCESSFUL OUTCOME    MeasurementFailure
    PROCEDURE CODE          id-Measurement
    CRITICALITY             reject
}

measurementReport   NRPPA-ELEMENTARY-PROCEDURE ::= {
    INITIATING MESSAGE      MeasurementReport
    PROCEDURE CODE          id-MeasurementReport
    CRITICALITY             ignore
}

measurementUpdate   NRPPA-ELEMENTARY-PROCEDURE ::= {
    INITIATING MESSAGE      MeasurementUpdate
    PROCEDURE CODE          id-MeasurementUpdate
    CRITICALITY             ignore
}

measurementAbort    NRPPA-ELEMENTARY-PROCEDURE ::= {
    INITIATING MESSAGE      MeasurementAbort
    PROCEDURE CODE          id-MeasurementAbort
    CRITICALITY             ignore
}

measurementFailureIndication    NRPPA-ELEMENTARY-PROCEDURE ::= {
    INITIATING MESSAGE      MeasurementFailureIndication
    PROCEDURE CODE          id-MeasurementFailureIndication
    CRITICALITY             ignore
}

tRPInformationExchange NRPPA-ELEMENTARY-PROCEDURE ::= {
    INITIATING MESSAGE     TRPInformationRequest
    SUCCESSFUL OUTCOME     TRPInformationResponse
    UNSUCCESSFUL OUTCOME   TRPInformationFailure
    PROCEDURE CODE         id-tRPInformationExchange
    CRITICALITY            reject
}

positioningActivation NRPPA-ELEMENTARY-PROCEDURE ::= {
    INITIATING MESSAGE      PositioningActivationRequest
    SUCCESSFUL OUTCOME      PositioningActivationResponse
    UNSUCCESSFUL OUTCOME    PositioningActivationFailure
    PROCEDURE CODE          id-positioningActivation
    CRITICALITY             reject
}

positioningDeactivation NRPPA-ELEMENTARY-PROCEDURE ::= {
    INITIATING MESSAGE      PositioningDeactivation




    PROCEDURE CODE           id-positioningDeactivation
    CRITICALITY              ignore
}

pRSConfigurationExchange NRPPA-ELEMENTARY-PROCEDURE ::= {
    INITIATING MESSAGE      PRSConfigurationRequest
    SUCCESSFUL OUTCOME      PRSConfigurationResponse
    UNSUCCESSFUL OUTCOME    PRSConfigurationFailure
    PROCEDURE CODE          id-pRSConfigurationExchange
    CRITICALITY             reject
}

measurementPreconfiguration NRPPA-ELEMENTARY-PROCEDURE ::= {
    INITIATING MESSAGE      MeasurementPreconfigurationRequired
    SUCCESSFUL OUTCOME      MeasurementPreconfigurationConfirm
    UNSUCCESSFUL OUTCOME        MeasurementPreconfigurationRefuse
    PROCEDURE CODE          id-measurementPreconfiguration
    CRITICALITY             reject
}

measurementActivation NRPPA-ELEMENTARY-PROCEDURE ::= {
    INITIATING MESSAGE      MeasurementActivation
    PROCEDURE CODE          id-measurementActivation
    CRITICALITY             ignore
}


END
