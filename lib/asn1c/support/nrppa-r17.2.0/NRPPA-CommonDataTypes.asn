NRPPA-CommonDataTypes {
itu-t (0) identified-organization (4) etsi (0) mobileDomain (0)
ngran-access (22) modules (3) nrppa (4) version1 (1) nrppa-CommonDataTypes (3)}

DEFINITIONS AUTOMATIC TAGS ::=

BEGIN

-- **************************************************************
--
-- Extension constants
--
-- **************************************************************

maxPrivateIEs                                     INTEGER ::= 65535
maxProtocolExtensions                             INTEGER ::= 65535
maxProtocolIEs                                    INTEGER ::= 65535

-- **************************************************************
--
-- Common Data Types
--
-- **************************************************************

Criticality      ::= ENUMERATED { reject, ignore, notify }

NRPPATransactionID       ::= INTEGER (0..32767)


Presence         ::= ENUMERATED { optional, conditional, mandatory }

PrivateIE-ID     ::= CHOICE {
    local            INTEGER (0.. maxPrivateIEs),
    global           OBJECT IDENTIFIER
}

ProcedureCode        ::= INTEGER (0..255)

ProtocolIE-ID        ::= INTEGER (0..maxProtocolIEs)

TriggeringMessage    ::= ENUMERATED { initiating-message, successful-outcome, unsuccessful-outcome}

END
