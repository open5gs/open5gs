NRPPA-Constants {
itu-t (0) identified-organization (4) etsi (0) mobileDomain (0)
ngran-access (22) modules (3) nrppa (4) version1 (1) nrppa-Constants (4) }

DEFINITIONS AUTOMATIC TAGS ::=

BEGIN

IMPORTS

    ProcedureCode,
    ProtocolIE-ID
FROM NRPPA-CommonDataTypes;

-- **************************************************************
--
-- Elementary Procedures
--
-- **************************************************************

id-errorIndication                                             ProcedureCode ::= 0
id-privateMessage                                              ProcedureCode ::= 1
id-e-CIDMeasurementInitiation                                  ProcedureCode ::= 2
id-e-CIDMeasurementFailureIndication                           ProcedureCode ::= 3
id-e-CIDMeasurementReport                                      ProcedureCode ::= 4
id-e-CIDMeasurementTermination                                 ProcedureCode ::= 5
id-oTDOAInformationExchange                                    ProcedureCode ::= 6
id-assistanceInformationControl                                ProcedureCode ::= 7
id-assistanceInformationFeedback                               ProcedureCode ::= 8
id-positioningInformationExchange                              ProcedureCode ::= 9
id-positioningInformationUpdate                                ProcedureCode ::= 10
id-Measurement                                                 ProcedureCode ::= 11
id-MeasurementReport                                           ProcedureCode ::= 12
id-MeasurementUpdate                                           ProcedureCode ::= 13
id-MeasurementAbort                                            ProcedureCode ::= 14
id-MeasurementFailureIndication                                ProcedureCode ::= 15
id-tRPInformationExchange                                      ProcedureCode ::= 16
id-positioningActivation                                       ProcedureCode ::= 17
id-positioningDeactivation                                     ProcedureCode ::= 18
id-pRSConfigurationExchange                                    ProcedureCode ::= 19
id-measurementPreconfiguration                                 ProcedureCode ::= 20
id-measurementActivation                                       ProcedureCode ::= 21

-- **************************************************************
--
-- Lists
--
-- **************************************************************

maxNrOfErrors                              INTEGER ::= 256
maxCellinRANnode                           INTEGER ::= 3840
maxIndexesReport                           INTEGER ::= 64
maxNoMeas                                  INTEGER ::= 64




maxCellReport                              INTEGER ::= 9
maxCellReportNR                            INTEGER ::= 9
maxnoOTDOAtypes                            INTEGER ::= 63
maxServCell                                INTEGER ::= 5
maxEUTRAMeas                               INTEGER ::= 8
maxGERANMeas                               INTEGER ::= 8
maxNRMeas                                  INTEGER ::= 8
maxUTRANMeas                               INTEGER ::= 8
maxWLANchannels                            INTEGER ::= 16
maxnoFreqHoppingBandsMinusOne              INTEGER ::= 7
maxNoPath                                  INTEGER ::= 2
maxNrOfPosSImessage                        INTEGER ::= 32
maxnoAssistInfoFailureListItems            INTEGER ::= 32
maxNrOfSegments                            INTEGER ::= 64
maxNrOfPosSIBs                             INTEGER ::= 32
maxNoOfMeasTRPs                            INTEGER ::= 64
maxnoTRPs                                  INTEGER ::= 65535
maxnoTRPInfoTypes                          INTEGER ::= 64
maxnoofAngleInfo                           INTEGER ::= 65535
maxnolcs-gcs-translation                   INTEGER ::= 3
maxnoBcastCell                             INTEGER ::= 16384
maxnoSRSTriggerStates                      INTEGER ::= 3
maxnoSpatialRelations                      INTEGER ::= 64
maxnoPosMeas                               INTEGER ::= 16384
maxnoSRS-Carriers                          INTEGER ::= 32
maxnoSCSs                                  INTEGER ::= 5
maxnoSRS-Resources                         INTEGER ::= 64
maxnoSRS-PosResources                      INTEGER ::= 64
maxnoSRS-ResourceSets                      INTEGER ::= 16
maxnoSRS-ResourcePerSet                    INTEGER ::= 16
maxnoSRS-PosResourceSets                   INTEGER ::= 16
maxnoSRS-PosResourcePerSet                 INTEGER ::= 16
maxPRS-ResourceSets                        INTEGER ::= 2
maxPRS-ResourcesPerSet                     INTEGER ::= 64
maxNoSSBs                                  INTEGER ::= 255
maxnoofPRSresourceSet                      INTEGER ::= 8
maxnoofPRSresource                         INTEGER ::= 64
maxnoofULAoAs                              INTEGER ::= 8
maxNoPathExtended                          INTEGER ::= 8
maxnoARPs                                  INTEGER ::= 16
maxnoUETEGs                                INTEGER ::= 256
maxnoTRPTEGs                               INTEGER ::= 8
maxFreqLayers                              INTEGER ::= 4
maxNumResourcesPerAngle                    INTEGER ::= 24
maxnoAzimuthAngles                         INTEGER ::= 3600
maxnoElevationAngles                       INTEGER ::= 1801
maxnoPRSTRPs                               INTEGER ::= 256



-- **************************************************************
--
-- IEs
--




-- **************************************************************

id-Cause                                                       ProtocolIE-ID ::= 0
id-CriticalityDiagnostics                                      ProtocolIE-ID ::= 1
id-LMF-UE-Measurement-ID                                       ProtocolIE-ID ::= 2
id-ReportCharacteristics                                       ProtocolIE-ID ::= 3
id-MeasurementPeriodicity                                      ProtocolIE-ID ::= 4
id-MeasurementQuantities                                       ProtocolIE-ID ::= 5
id-RAN-UE-Measurement-ID                                       ProtocolIE-ID ::= 6
id-E-CID-MeasurementResult                                     ProtocolIE-ID ::= 7
id-OTDOACells                                                  ProtocolIE-ID ::= 8
id-OTDOA-Information-Type-Group                                ProtocolIE-ID ::= 9
id-OTDOA-Information-Type-Item                                 ProtocolIE-ID ::= 10
id-MeasurementQuantities-Item                                  ProtocolIE-ID ::= 11
id-RequestedSRSTransmissionCharacteristics                     ProtocolIE-ID ::= 12
id-Cell-Portion-ID                                             ProtocolIE-ID ::= 14
id-OtherRATMeasurementQuantities                               ProtocolIE-ID ::= 15
id-OtherRATMeasurementQuantities-Item                          ProtocolIE-ID ::= 16
id-OtherRATMeasurementResult                                   ProtocolIE-ID ::= 17
id-WLANMeasurementQuantities                                   ProtocolIE-ID ::= 19
id-WLANMeasurementQuantities-Item                              ProtocolIE-ID ::= 20
id-WLANMeasurementResult                                       ProtocolIE-ID ::= 21
id-TDD-Config-EUTRA-Item                                       ProtocolIE-ID ::= 22
id-Assistance-Information                                      ProtocolIE-ID ::= 23
id-Broadcast                                                   ProtocolIE-ID ::= 24
id-AssistanceInformationFailureList                            ProtocolIE-ID ::= 25
id-SRSConfiguration                                            ProtocolIE-ID ::= 26
id-MeasurementResult                                           ProtocolIE-ID ::= 27
id-TRP-ID                                                      ProtocolIE-ID ::= 28
id-TRPInformationTypeListTRPReq                                ProtocolIE-ID ::= 29
id-TRPInformationListTRPResp                                   ProtocolIE-ID ::= 30
id-MeasurementBeamInfoRequest                                  ProtocolIE-ID ::= 31
id-ResultSS-RSRP                                               ProtocolIE-ID ::= 32
id-ResultSS-RSRQ                                               ProtocolIE-ID ::= 33
id-ResultCSI-RSRP                                              ProtocolIE-ID ::= 34
id-ResultCSI-RSRQ                                              ProtocolIE-ID ::= 35
id-AngleOfArrivalNR                                            ProtocolIE-ID ::= 36
id-GeographicalCoordinates                                     ProtocolIE-ID ::= 37
id-PositioningBroadcastCells                                   ProtocolIE-ID ::= 38
id-LMF-Measurement-ID                                          ProtocolIE-ID ::= 39
id-RAN-Measurement-ID                                          ProtocolIE-ID ::= 40
id-TRP-MeasurementRequestList                                  ProtocolIE-ID ::= 41
id-TRP-MeasurementResponseList                                 ProtocolIE-ID ::= 42
id-TRP-MeasurementReportList                                   ProtocolIE-ID ::= 43
id-SRSType                                                     ProtocolIE-ID ::= 44
id-ActivationTime                                              ProtocolIE-ID ::= 45
id-SRSResourceSetID                                            ProtocolIE-ID ::= 46
id-TRPList                                                     ProtocolIE-ID ::= 47
id-SRSSpatialRelation                                          ProtocolIE-ID ::= 48
id-SystemFrameNumber                                           ProtocolIE-ID ::= 49
id-SlotNumber                                                  ProtocolIE-ID ::= 50
id-SRSResourceTrigger                                          ProtocolIE-ID ::= 51
id-TRPMeasurementQuantities                                    ProtocolIE-ID ::= 52
id-AbortTransmission                                           ProtocolIE-ID ::= 53




id-SFNInitialisationTime                            ProtocolIE-ID ::= 54
id-ResultNR                                         ProtocolIE-ID ::= 55
id-ResultEUTRA                                      ProtocolIE-ID ::= 56
id-TRPInformationTypeItem                           ProtocolIE-ID ::= 57
id-CGI-NR                                           ProtocolIE-ID ::= 58
id-SFNInitialisationTime-NR                         ProtocolIE-ID ::= 59
id-Cell-ID                                          ProtocolIE-ID ::= 60
id-SrsFrequency                                     ProtocolIE-ID ::= 61
id-TRPType                                          ProtocolIE-ID ::= 62
id-SRSSpatialRelationPerSRSResource                 ProtocolIE-ID ::= 63
id-MeasurementPeriodicityExtended                   ProtocolIE-ID ::= 64
id-PRS-Resource-ID                                  ProtocolIE-ID ::= 65
id-PRSTRPList                                       ProtocolIE-ID ::= 66
id-PRSTransmissionTRPList                           ProtocolIE-ID ::= 67
id-OnDemandPRS                                  ProtocolIE-ID ::= 68
id-AoA-SearchWindow                                 ProtocolIE-ID ::= 69
id-TRP-MeasurementUpdateList                        ProtocolIE-ID ::= 70
id-ZoA                                              ProtocolIE-ID ::= 71
id-ResponseTime                                     ProtocolIE-ID ::= 72
id-UEReportingInformation                           ProtocolIE-ID ::= 73
id-MultipleULAoA                                    ProtocolIE-ID ::= 74
id-UL-SRS-RSRPP                                     ProtocolIE-ID ::= 75
id-SRSResourcetype                                  ProtocolIE-ID ::= 76
id-ExtendedAdditionalPathList                       ProtocolIE-ID ::= 77
id-ARPLocationInfo                                  ProtocolIE-ID ::= 78
id-ARP-ID                                           ProtocolIE-ID ::= 79
id-LoS-NLoSInformation                              ProtocolIE-ID ::= 80
id-UETxTEGAssociationList                           ProtocolIE-ID ::= 81
id-NumberOfTRPRxTEG                                 ProtocolIE-ID ::= 82
id-NumberOfTRPRxTxTEG                               ProtocolIE-ID ::= 83
id-TRPTxTEGAssociation                              ProtocolIE-ID ::= 84
id-TRPTEGIDInformation                              ProtocolIE-ID ::= 85
id-TRPRXTEGID                                       ProtocolIE-ID ::= 86
id-TRP-PRS-Information-List                         ProtocolIE-ID ::= 87
id-PRS-Measurements-Info-List                       ProtocolIE-ID ::= 88
id-PRSConfigRequestType                             ProtocolIE-ID ::= 89
id-UE-TEG-Info-Request                              ProtocolIE-ID ::= 90
id-MeasurementTimeOccasion                          ProtocolIE-ID ::= 91
id-MeasurementCharacteristicsRequestIndicator       ProtocolIE-ID ::= 92
id-TRPBeamAntennaInformation                        ProtocolIE-ID ::= 93
id-NR-TADV                                          ProtocolIE-ID ::= 94
id-MeasurementAmount                                ProtocolIE-ID ::= 95
id-pathPower                                        ProtocolIE-ID ::= 96
id-PreconfigurationResult                           ProtocolIE-ID ::= 97
id-RequestType                                      ProtocolIE-ID ::= 98
id-UE-TEG-ReportingPeriodicity                      ProtocolIE-ID ::= 99
id-SRSPortIndex                                     ProtocolIE-ID ::= 100
id-TRPTxTimingErrorMargin                           ProtocolIE-ID ::= 101
id-TRPRxTimingErrorMargin                           ProtocolIE-ID ::= 102
id-TRPRxTxTimingErrorMargin                         ProtocolIE-ID ::= 103
id-UETxTimingErrorMargin                            ProtocolIE-ID ::= 104
id-MeasurementPeriodicityNR-AoA                     ProtocolIE-ID ::= 105






END
