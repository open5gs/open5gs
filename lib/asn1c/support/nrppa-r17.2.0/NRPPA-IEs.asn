NRPPA-IEs {
itu-t (0) identified-organization (4) etsi (0) mobileDomain (0)
ngran-access (22) modules (3) nrppa (4) version1 (1) nrppa-IEs (2) }




DEFINITIONS AUTOMATIC TAGS ::=

BEGIN

IMPORTS

    id-MeasurementQuantities-Item,
    id-CGI-NR,
    id-SFNInitialisationTime-NR,
    id-GeographicalCoordinates,
    id-ResultSS-RSRP,
    id-ResultSS-RSRQ,
    id-ResultCSI-RSRP,
    id-ResultCSI-RSRQ,
    id-AngleOfArrivalNR,
    id-ResultNR,
    id-ResultEUTRA,
    maxCellinRANnode,
    maxCellReport,
    maxNrOfErrors,
    maxNoMeas,
    maxnoOTDOAtypes,
    maxServCell,
    id-OtherRATMeasurementQuantities-Item,
    id-WLANMeasurementQuantities-Item,
    maxGERANMeas,
    maxUTRANMeas,
    maxWLANchannels,
    maxnoFreqHoppingBandsMinusOne,
    id-TDD-Config-EUTRA-Item,
    maxNrOfPosSImessage,
    maxnoAssistInfoFailureListItems,
    maxNrOfSegments,
    maxNrOfPosSIBs,
    maxnoPosMeas,
    maxnoTRPs,
    maxnoTRPInfoTypes,
    maxNoOfMeasTRPs,
    maxNoPath,
    maxnoofAngleInfo,
    maxnolcs-gcs-translation,
    maxnoBcastCell,
    maxnoSRSTriggerStates,
    maxnoSpatialRelations,
    maxNRMeas,
    maxEUTRAMeas,
    maxIndexesReport,
    maxCellReportNR,
    maxnoSRS-Carriers,
    maxnoSCSs,
    maxnoSRS-Resources,
    maxnoSRS-PosResources,
    maxnoSRS-ResourceSets,




    maxnoSRS-ResourcePerSet,
    maxnoSRS-PosResourceSets,
    maxnoSRS-PosResourcePerSet,
    maxPRS-ResourceSets,
    maxPRS-ResourcesPerSet,
    maxNoSSBs,
    maxnoofPRSresourceSet,
    maxnoofPRSresource,
    maxnoofULAoAs,
    maxNoPathExtended,
    maxnoARPs,
    maxnoTRPTEGs,
    maxnoUETEGs,
    maxFreqLayers,
    maxnoPRSTRPs,
    maxNumResourcesPerAngle,
    maxnoAzimuthAngles,
    maxnoElevationAngles,
    id-Cell-ID,
    id-TRPInformationTypeItem,
    id-SrsFrequency,
    id-TRPType,
    id-SRSSpatialRelationPerSRSResource,
    id-PRS-Resource-ID,
    id-OnDemandPRS,
    id-AoA-SearchWindow,
    id-ZoA,
    id-MultipleULAoA,
    id-UL-SRS-RSRPP,
    id-SRSResourcetype,
    id-ExtendedAdditionalPathList,
    id-ARPLocationInfo,
    id-ARP-ID,
    id-LoS-NLoSInformation,
    id-NumberOfTRPRxTEG,
    id-NumberOfTRPRxTxTEG,
    id-TRPTxTEGAssociation,
    id-TRPTEGIDInformation,
    id-TRPRXTEGID,
    id-TRPBeamAntennaInformation,
    id-NR-TADV,
    id-pathPower,
    id-SRSPortIndex,
    id-TRPTxTimingErrorMargin,
    id-TRPRxTimingErrorMargin,
    id-TRPRxTxTimingErrorMargin,
    id-UETxTimingErrorMargin




FROM NRPPA-Constants

    Criticality,




    NRPPATransactionID,
    ProcedureCode,
    ProtocolIE-ID,
    TriggeringMessage

FROM NRPPA-CommonDataTypes

    ProtocolExtensionContainer{},
    ProtocolIE-Single-Container{},

    NRPPA-PROTOCOL-EXTENSION,
    NRPPA-PROTOCOL-IES

FROM NRPPA-Containers;

-- A

AbortTransmission ::= CHOICE {
    deactivateSRSResourceSetID        SRSResourceSetID,
    releaseALL                        NULL,
    choice-extension                              ProtocolIE-Single-Container { { AbortTransmission-ExtIEs } }
}

AbortTransmission-ExtIEs NRPPA-PROTOCOL-IES ::= {
    ...
}

ActiveULBWP ::= SEQUENCE {
    locationAndBandwidth          INTEGER (0..37949,...),
    subcarrierSpacing             ENUMERATED {kHz15, kHz30, kHz60, kHz120,...},
    cyclicPrefix                  ENUMERATED {normal, extended},
    txDirectCurrentLocation       INTEGER (0..3301,...),
    shift7dot5kHz                 ENUMERATED {true, ...} OPTIONAL,
    sRSConfig                     SRSConfig,
    iE-Extensions                 ProtocolExtensionContainer { { ActiveULBWP-ExtIEs} } OPTIONAL,
    ...
}

ActiveULBWP-ExtIEs NRPPA-PROTOCOL-EXTENSION ::= {
    ...
}


AdditionalPathList ::= SEQUENCE (SIZE (1.. maxNoPath)) OF AdditionalPathListItem


AdditionalPathListItem ::= SEQUENCE {
    relativeTimeOfPath RelativePathDelay,
    pathQuality         TrpMeasurementQuality   OPTIONAL,
    iE-Extensions       ProtocolExtensionContainer { { AdditionalPathListItem-ExtIEs} } OPTIONAL,
    ...
}

AdditionalPathListItem-ExtIEs NRPPA-PROTOCOL-EXTENSION ::= {




    { ID id-MultipleULAoA    CRITICALITY ignore EXTENSION MultipleULAoA PRESENCE optional}|
    { ID id-pathPower        CRITICALITY ignore EXTENSION UL-SRS-RSRPP PRESENCE optional},
    ...
}

ExtendedAdditionalPathList ::= SEQUENCE (SIZE (1.. maxNoPathExtended)) OF ExtendedAdditionalPathList-Item


ExtendedAdditionalPathList-Item ::= SEQUENCE {
    relativeTimeOfPath RelativePathDelay,
    pathQuality         TrpMeasurementQuality   OPTIONAL,
    multipleULAoA       MultipleULAoA           OPTIONAL,
    pathPower           UL-SRS-RSRPP            OPTIONAL,
    iE-Extensions       ProtocolExtensionContainer { { ExtendedAdditionalPathList-Item-ExtIEs} } OPTIONAL,
    ...
}

ExtendedAdditionalPathList-Item-ExtIEs NRPPA-PROTOCOL-EXTENSION ::= {
    ...
}

AoA-AssistanceInfo ::= SEQUENCE {
    angleMeasurement    AngleMeasurementType,
    lCS-to-GCS-Translation LCS-to-GCS-Translation       OPTIONAL,
    iE-Extensions               ProtocolExtensionContainer { { AoA-AssistanceInfo-ExtIEs } } OPTIONAL,
    ...
}

AoA-AssistanceInfo-ExtIEs NRPPA-PROTOCOL-EXTENSION ::= {
    ...
}

AperiodicSRSResourceTriggerList ::= SEQUENCE (SIZE(1..maxnoSRSTriggerStates)) OF AperiodicSRSResourceTrigger

AperiodicSRSResourceTrigger ::= INTEGER (1..3)

AngleMeasurementType ::= CHOICE {
    expected-ULAoA      Expected-UL-AoA,
    expected-ZoA        Expected-ZoA-only,
    choice-extension ProtocolIE-Single-Container { { AngleMeasurementType-ExtIEs } }
}

AngleMeasurementType-ExtIEs NRPPA-PROTOCOL-IES ::= {
...
}

Expected-UL-AoA ::= SEQUENCE {
    expected-Azimuth-AoA        Expected-Azimuth-AoA,
    expected-Zenith-AoA     Expected-Zenith-AoA     OPTIONAL,
    iE-extensions       ProtocolExtensionContainer { { Expected-UL-AoA-ExtIEs } }   OPTIONAL,
    ...
}

Expected-UL-AoA-ExtIEs NRPPA-PROTOCOL-EXTENSION ::= {




    ...
}

Expected-ZoA-only ::= SEQUENCE {
    expected-ZoA-only   Expected-Zenith-AoA,
    iE-extensions       ProtocolExtensionContainer { { Expected-ZoA-only-ExtIEs } } OPTIONAL,
    ...
}

Expected-ZoA-only-ExtIEs NRPPA-PROTOCOL-EXTENSION ::= {
    ...
}

Expected-Azimuth-AoA ::= SEQUENCE {
    expected-Azimuth-AoA-value          Expected-Value-AoA,
    expected-Azimuth-AoA-uncertainty        Uncertainty-range-AoA,
    iE-extensions       ProtocolExtensionContainer { { Expected-Azimuth-AoA-ExtIEs } }    OPTIONAL,
    ...
}

Expected-Azimuth-AoA-ExtIEs NRPPA-PROTOCOL-EXTENSION ::= {
    ...
}

Expected-Zenith-AoA ::= SEQUENCE {
    expected-Zenith-AoA-value           Expected-Value-ZoA,
    expected-Zenith-AoA-uncertainty     Uncertainty-range-ZoA,
    iE-extensions       ProtocolExtensionContainer { { Expected-Zenith-AoA-ExtIEs } }     OPTIONAL,
    ...
}

Expected-Zenith-AoA-ExtIEs NRPPA-PROTOCOL-EXTENSION ::= {
    ...
}

ARP-ID ::= INTEGER (1..16, ...)

ARPLocationInformation ::= SEQUENCE (SIZE (1..maxnoARPs)) OF ARPLocationInformation-Item

ARPLocationInformation-Item ::= SEQUENCE {
    aRP-ID              ARP-ID,
    aRPLocationType     ARPLocationType,
    iE-Extensions       ProtocolExtensionContainer { { ARPLocationInformation-ExtIEs} } OPTIONAL,
    ...
}

ARPLocationInformation-ExtIEs NRPPA-PROTOCOL-EXTENSION ::= {
    ...
}

ARPLocationType ::= CHOICE {
    aRPPositionRelativeGeodetic            RelativeGeodeticLocation,
    aRPPositionRelativeCartesian           RelativeCartesianLocation,
    choice-extension                       ProtocolIE-Single-Container { { ARPLocationType-ExtIEs } }




}

ARPLocationType-ExtIEs NRPPA-PROTOCOL-IES ::= {
    ...
}

Assistance-Information ::= SEQUENCE {
    systemInformation               SystemInformation,
    iE-Extensions                   ProtocolExtensionContainer { { Assistance-Information-ExtIEs} } OPTIONAL,
    ...
}

Assistance-Information-ExtIEs NRPPA-PROTOCOL-EXTENSION ::= {
    ...
}

AssistanceInformationFailureList ::= SEQUENCE (SIZE (1..maxnoAssistInfoFailureListItems)) OF SEQUENCE {
    posSIB-Type                     PosSIB-Type,
    outcome                         Outcome,
    iE-Extensions                   ProtocolExtensionContainer { {AssistanceInformationFailureList-ExtIEs} } OPTIONAL,
    ...
}

AssistanceInformationFailureList-ExtIEs NRPPA-PROTOCOL-EXTENSION ::= {
    ...
}

AssistanceInformationMetaData ::= SEQUENCE {
    encrypted           ENUMERATED {true, ...} OPTIONAL,
    gNSSID              ENUMERATED {gps, sbas, qzss, galileo, glonass, bds, navic, ...} OPTIONAL,
    sBASID              ENUMERATED {waas, egnos, msas, gagan, ...}                  OPTIONAL,
    iE-Extensions       ProtocolExtensionContainer { { AssistanceInformationMetaData-ExtIEs} } OPTIONAL,
    ...
}

AssistanceInformationMetaData-ExtIEs NRPPA-PROTOCOL-EXTENSION ::= {
    ...
}



-- B

BandwidthSRS ::= CHOICE {
    fR1     ENUMERATED {mHz5, mHz10, mHz20, mHz40, mHz50, mHz80, mHz100, ...},
    fR2     ENUMERATED {mHz50, mHz100, mHz200, mHz400, ...},
    choice-extension        ProtocolIE-Single-Container { { BandwidthSRS-ExtIEs } }
}

BandwidthSRS-ExtIEs NRPPA-PROTOCOL-IES ::= {
    ...
}

BCCH ::= INTEGER (0..1023, ...)





Broadcast ::= ENUMERATED {
    start,
    stop,
    ...
}

BroadcastPeriodicity ::= ENUMERATED {
    ms80,
    ms160,
    ms320,
    ms640,
    ms1280,
    ms2560,
    ms5120,
    ...
}

PositioningBroadcastCells ::= SEQUENCE (SIZE (1..maxnoBcastCell)) OF NG-RAN-CGI

BSSID ::= OCTET STRING (SIZE(6))

-- C

CarrierFreq ::= SEQUENCE {
    pointA              INTEGER (0..3279165),
    offsetToCarrier     INTEGER (0..2199, ...),
    iE-Extensions       ProtocolExtensionContainer { {CarrierFreq-ExtIEs} } OPTIONAL,
    ...
}

CarrierFreq-ExtIEs NRPPA-PROTOCOL-EXTENSION ::= {
    ...
}

Cause ::= CHOICE {
    radioNetwork         CauseRadioNetwork,
    protocol             CauseProtocol,
    misc                 CauseMisc,
    choice-Extension     ProtocolIE-Single-Container {{ Cause-ExtensionIE }}
}

Cause-ExtensionIE NRPPA-PROTOCOL-IES ::= {
    ...
}

CauseMisc ::= ENUMERATED {
    unspecified,
    ...
}

CauseProtocol ::= ENUMERATED {
    transfer-syntax-error,
    abstract-syntax-error-reject,




    abstract-syntax-error-ignore-and-notify,
    message-not-compatible-with-receiver-state,
    semantic-error,
    unspecified,
    abstract-syntax-error-falsely-constructed-message,
    ...
}

CauseRadioNetwork ::= ENUMERATED {
    unspecified,
    requested-item-not-supported,
    requested-item-temporarily-not-available,
    ...,
    serving-NG-RAN-node-changed,
    requested-item-not-supported-on-time

}

Cell-Portion-ID ::= INTEGER (0..4095,...)

CGI-EUTRA ::= SEQUENCE {
    pLMN-Identity                 PLMN-Identity,
    eUTRAcellIdentifier           EUTRACellIdentifier,
    iE-Extensions                 ProtocolExtensionContainer { {CGI-EUTRA-ExtIEs} } OPTIONAL,
    ...
}

CGI-EUTRA-ExtIEs NRPPA-PROTOCOL-EXTENSION ::= {
    ...
}


CGI-NR ::= SEQUENCE {
    pLMN-Identity                 PLMN-Identity,
    nRcellIdentifier              NRCellIdentifier,
    iE-Extensions                 ProtocolExtensionContainer { {CGI-NR-ExtIEs} } OPTIONAL,
    ...
}

CGI-NR-ExtIEs NRPPA-PROTOCOL-EXTENSION ::= {
    ...
}


CPLength-EUTRA ::= ENUMERATED {
    normal,
    extended,
    ...
}

CriticalityDiagnostics ::= SEQUENCE {
    procedureCode                   ProcedureCode                    OPTIONAL,
    triggeringMessage               TriggeringMessage                OPTIONAL,
    procedureCriticality            Criticality                  OPTIONAL,




    nrppatransactionID                NRPPATransactionID              OPTIONAL,
    iEsCriticalityDiagnostics         CriticalityDiagnostics-IE-List OPTIONAL,
    iE-Extensions                     ProtocolExtensionContainer { {CriticalityDiagnostics-ExtIEs} }   OPTIONAL,
    ...
}


CriticalityDiagnostics-ExtIEs NRPPA-PROTOCOL-EXTENSION ::= {
    ...
}

CriticalityDiagnostics-IE-List ::= SEQUENCE (SIZE (1..maxNrOfErrors)) OF
    SEQUENCE {
        iECriticality           Criticality,
        iE-ID                   ProtocolIE-ID,
        typeOfError             TypeOfError,
        iE-Extensions           ProtocolExtensionContainer { {CriticalityDiagnostics-IE-List-ExtIEs} } OPTIONAL,
        ...
}

CriticalityDiagnostics-IE-List-ExtIEs NRPPA-PROTOCOL-EXTENSION ::= {
    ...
}


-- D

DL-Bandwidth-EUTRA ::= ENUMERATED {
    bw6,
    bw15,
    bw25,
    bw50,
    bw75,
    bw100,
    ...
}

DL-PRS ::= SEQUENCE {
    prsid                    INTEGER (0..255),
    dl-PRSResourceSetID      PRS-Resource-Set-ID,
    dl-PRSResourceID         PRS-Resource-ID     OPTIONAL,
    iE-Extensions            ProtocolExtensionContainer { {DL-PRS-ExtIEs} }     OPTIONAL,
    ...
}

DL-PRS-ExtIEs NRPPA-PROTOCOL-EXTENSION ::= {
    ...
}

DL-PRSMutingPattern ::= CHOICE {
    two                 BIT STRING (SIZE(2)),
    four                BIT STRING (SIZE(4)),
    six                 BIT STRING (SIZE(6)),
    eight               BIT STRING (SIZE(8)),




    sixteen              BIT STRING (SIZE(16)),
    thirty-two           BIT STRING (SIZE(32)),
    choice-extension                              ProtocolIE-Single-Container { { DL-PRSMutingPattern-ExtIEs } }
}

DL-PRSMutingPattern-ExtIEs NRPPA-PROTOCOL-IES ::= {
    ...
}

DLPRSResourceCoordinates ::= SEQUENCE {
    listofDL-PRSResourceSetARP      SEQUENCE (SIZE(1.. maxPRS-ResourceSets)) OF DLPRSResourceSetARP,
    iE-Extensions                   ProtocolExtensionContainer { { DLPRSResourceCoordinates-ExtIEs } } OPTIONAL,
    ...
}

DLPRSResourceCoordinates-ExtIEs NRPPA-PROTOCOL-EXTENSION ::= {
    ...
}

DLPRSResourceSetARP ::= SEQUENCE {
    dl-PRSResourceSetID               PRS-Resource-Set-ID,
    dL-PRSResourceSetARPLocation      DL-PRSResourceSetARPLocation,
    listofDL-PRSResourceARP           SEQUENCE (SIZE(1.. maxPRS-ResourcesPerSet)) OF DLPRSResourceARP,
    iE-Extensions                     ProtocolExtensionContainer { { DLPRSResourceSetARP-ExtIEs } } OPTIONAL,
    ...
}

DLPRSResourceSetARP-ExtIEs NRPPA-PROTOCOL-EXTENSION ::= {
    ...
}


DL-PRSResourceSetARPLocation ::= CHOICE {
    relativeGeodeticLocation            RelativeGeodeticLocation,
    relativeCartesianLocation           RelativeCartesianLocation,
    choice-Extension                    ProtocolIE-Single-Container { { DL-PRSResourceSetARPLocation-ExtIEs } }
}

DL-PRSResourceSetARPLocation-ExtIEs NRPPA-PROTOCOL-IES ::= {
    ...
}


DLPRSResourceARP ::= SEQUENCE {
    dl-PRSResourceID            PRS-Resource-ID,
    dL-PRSResourceARPLocation   DL-PRSResourceARPLocation,
    iE-Extensions               ProtocolExtensionContainer { { DLPRSResourceARP-ExtIEs } } OPTIONAL,
    ...
}

DLPRSResourceARP-ExtIEs NRPPA-PROTOCOL-EXTENSION ::= {
    ...
}





DL-PRSResourceARPLocation ::= CHOICE {
    relativeGeodeticLocation               RelativeGeodeticLocation,
    relativeCartesianLocation              RelativeCartesianLocation,
    choice-Extension                       ProtocolIE-Single-Container { { DL-PRSResourceARPLocation-ExtIEs } }
}

DL-PRSResourceARPLocation-ExtIEs NRPPA-PROTOCOL-IES ::= {
    ...
}

-- E

E-CID-MeasurementResult ::= SEQUENCE {
    servingCell-ID                  NG-RAN-CGI,
    servingCellTAC                  TAC,
    nG-RANAccessPointPosition       NG-RANAccessPointPosition   OPTIONAL,
    measuredResults                 MeasuredResults             OPTIONAL,
    iE-Extensions                   ProtocolExtensionContainer { { E-CID-MeasurementResult-ExtIEs} } OPTIONAL,
    ...
}

E-CID-MeasurementResult-ExtIEs NRPPA-PROTOCOL-EXTENSION ::= {
    { ID id-GeographicalCoordinates CRITICALITY ignore EXTENSION GeographicalCoordinates PRESENCE optional},
    ...
}

EUTRACellIdentifier ::= BIT STRING (SIZE (28))

EARFCN ::= INTEGER (0..262143, ...)

Expected-Value-AoA ::= INTEGER (0..3599)

Expected-Value-ZoA ::= INTEGER (0..1799)


-- F

-- G

GeographicalCoordinates ::= SEQUENCE {
    tRPPositionDefinitionType   TRPPositionDefinitionType,
    dLPRSResourceCoordinates    DLPRSResourceCoordinates    OPTIONAL,
    iE-Extensions               ProtocolExtensionContainer { { GeographicalCoordinates-ExtIEs } } OPTIONAL,
    ...
}

GeographicalCoordinates-ExtIEs NRPPA-PROTOCOL-EXTENSION ::= {
    { ID id-ARPLocationInfo     CRITICALITY ignore EXTENSION ARPLocationInformation       PRESENCE optional},
    ...
}


GNB-RxTxTimeDiff ::= SEQUENCE {





    rxTxTimeDiff         GNBRxTxTimeDiffMeas,
    additionalPathList   AdditionalPathList OPTIONAL,
    iE-Extensions        ProtocolExtensionContainer { { GNB-RxTxTimeDiff-ExtIEs} }   OPTIONAL,
    ...
}

GNB-RxTxTimeDiff-ExtIEs NRPPA-PROTOCOL-EXTENSION ::= {
    { ID id-ExtendedAdditionalPathList CRITICALITY ignore EXTENSION ExtendedAdditionalPathList PRESENCE optional}|
    { ID id-TRPTEGIDInformation     CRITICALITY ignore EXTENSION TRPTEGIDInformation   PRESENCE optional },

    ...
}


GNBRxTxTimeDiffMeas ::= CHOICE {
    k0          INTEGER (0.. 1970049),
    k1          INTEGER (0.. 985025),
    k2          INTEGER (0.. 492513),
    k3          INTEGER (0.. 246257),
    k4          INTEGER (0.. 123129),
    k5          INTEGER (0.. 61565),
    choice-extension        ProtocolIE-Single-Container { { GNBRxTxTimeDiffMeas-ExtIEs } }
}

GNBRxTxTimeDiffMeas-ExtIEs        NRPPA-PROTOCOL-IES ::= {
    ...
}

-- H

HESSID ::= OCTET STRING (SIZE(6))

-- I

-- J

-- K

-- L

LCS-to-GCS-Translation::= SEQUENCE {
    alpha               INTEGER (0..3599),
    beta                INTEGER (0..3599),
    gamma               INTEGER (0..3599),
    iE-Extensions       ProtocolExtensionContainer { { LCS-to-GCS-Translation-ExtIEs} } OPTIONAL,
    ...
}

LCS-to-GCS-Translation-ExtIEs NRPPA-PROTOCOL-EXTENSION ::= {
    ...
}

LCS-to-GCS-TranslationItem::= SEQUENCE {
    alpha               INTEGER (0..359),




    alphaFine            INTEGER (0..9)      OPTIONAL,
    beta                 INTEGER (0..359),
    betaFine             INTEGER (0..9)      OPTIONAL,
    gamma                INTEGER (0..359),
    gammaFine            INTEGER (0..9)      OPTIONAL,
    iE-Extensions        ProtocolExtensionContainer { { LCS-to-GCS-TranslationItem-ExtIEs} } OPTIONAL,
    ...
}

LCS-to-GCS-TranslationItem-ExtIEs NRPPA-PROTOCOL-EXTENSION ::= {
    ...
}

LocationUncertainty ::= SEQUENCE {
    horizontalUncertainty       INTEGER (0..255),
    horizontalConfidence        INTEGER (0..100),
    verticalUncertainty         INTEGER (0..255),
    verticalConfidence          INTEGER (0..100),
    iE-Extensions               ProtocolExtensionContainer { { LocationUncertainty-ExtIEs} } OPTIONAL,
    ...
}

LocationUncertainty-ExtIEs NRPPA-PROTOCOL-EXTENSION ::= {
    ...
}

LoS-NLoSIndicatorHard ::= ENUMERATED {nlos, los}

LoS-NLoSIndicatorSoft ::= INTEGER (0..10)

LoS-NLoSInformation ::= CHOICE {
    loS-NLoSIndicatorSoft       LoS-NLoSIndicatorSoft,
    loS-NLoSIndicatorHard       LoS-NLoSIndicatorHard,
    choice-Extension        ProtocolIE-Single-Container {{ LoS-NLoSInformation-ExtIEs}}

}

LoS-NLoSInformation-ExtIEs NRPPA-PROTOCOL-IES ::= {
    ...
}


-- M

Measurement-ID ::= INTEGER (1.. 65536, ...)

MeasurementAmount   ::= ENUMERATED {ma0, ma1, ma2, ma4, ma8, ma16, ma32, ma64}

MeasurementBeamInfoRequest ::= ENUMERATED {true, ...}

MeasurementBeamInfo ::= SEQUENCE {
    pRS-Resource-ID             PRS-Resource-ID     OPTIONAL,
    pRS-Resource-Set-ID         PRS-Resource-Set-ID OPTIONAL,
    sSB-Index                   SSB-Index           OPTIONAL,




    iE-Extensions                                 ProtocolExtensionContainer { { MeasurementBeamInfo-ExtIEs} } OPTIONAL,
    ...
}

MeasurementBeamInfo-ExtIEs NRPPA-PROTOCOL-EXTENSION ::= {
    ...
}


MeasurementPeriodicity ::= ENUMERATED {
    ms120,
    ms240,
    ms480,
    ms640,
    ms1024,
    ms2048,
    ms5120,
    ms10240,
    min1,
    min6,
    min12,
    min30,
    min60,
    ...,
    ms20480,
    ms40960,
    extended
}

MeasurementPeriodicityExtended ::= ENUMERATED {
    ms160,
    ms320,
    ms1280,
    ms2560,
    ms61440,
    ms81920,
    ms368640,
    ms737280,
    ms1843200,
    ...

}

MeasurementPeriodicityNR-AoA ::= ENUMERATED {
    ms160,
    ms320,
    ms640,
    ms1280,
    ms2560,
    ms5120,
    ms10240,
    ms20480,
    ms40960,
    ms61440,




    ms81920,
    ms368640,
    ms737280,
    ms1843200,
    ...

}

MeasurementQuantities ::= SEQUENCE (SIZE (1.. maxNoMeas)) OF ProtocolIE-Single-Container { {MeasurementQuantities-ItemIEs} }

MeasurementQuantities-ItemIEs NRPPA-PROTOCOL-IES ::= {
    { ID id-MeasurementQuantities-Item CRITICALITY reject   TYPE MeasurementQuantities-Item    PRESENCE mandatory}
}

MeasurementQuantities-Item ::= SEQUENCE {
    measurementQuantitiesValue                 MeasurementQuantitiesValue,
    iE-Extensions                              ProtocolExtensionContainer { { MeasurementQuantitiesValue-ExtIEs} } OPTIONAL,
    ...
}

MeasurementQuantitiesValue-ExtIEs NRPPA-PROTOCOL-EXTENSION ::= {
    ...
}

MeasurementQuantitiesValue ::= ENUMERATED {
    cell-ID,
    angleOfArrival,
    timingAdvanceType1,
    timingAdvanceType2,
    rSRP,
    rSRQ,
    ... ,
    sS-RSRP,
    sS-RSRQ,
    cSI-RSRP,
    cSI-RSRQ,
    angleOfArrivalNR,
    timingAdvanceNR
}

MeasurementTimeOccasion ::= ENUMERATED {o1, o4, ...}

MeasurementCharacteristicsRequestIndicator ::= BIT STRING (SIZE (16))

MeasuredResults ::= SEQUENCE (SIZE (1.. maxNoMeas)) OF MeasuredResultsValue

MeasuredResultsValue ::= CHOICE {
    valueAngleOfArrival-EUTRA               INTEGER (0..719),
    valueTimingAdvanceType1-EUTRA           INTEGER (0..7690),
    valueTimingAdvanceType2-EUTRA           INTEGER (0..7690),
    resultRSRP-EUTRA                        ResultRSRP-EUTRA,
    resultRSRQ-EUTRA                        ResultRSRQ-EUTRA,
    choice-Extension            ProtocolIE-Single-Container {{ MeasuredResultsValue-ExtensionIE }}
}





MeasuredResultsValue-ExtensionIE NRPPA-PROTOCOL-IES ::= {
{ ID id-ResultSS-RSRP       CRITICALITY ignore TYPE ResultSS-RSRP      PRESENCE mandatory }|
    { ID id-ResultSS-RSRQ       CRITICALITY ignore TYPE ResultSS-RSRQ      PRESENCE mandatory    }|
    { ID id-ResultCSI-RSRP      CRITICALITY ignore TYPE ResultCSI-RSRP     PRESENCE mandatory    }|
    { ID id-ResultCSI-RSRQ      CRITICALITY ignore TYPE ResultCSI-RSRQ     PRESENCE mandatory    }|
    { ID id-AngleOfArrivalNR    CRITICALITY ignore TYPE UL-AoA             PRESENCE mandatory    }|
    { ID id-NR-TADV             CRITICALITY ignore TYPE NR-TADV            PRESENCE mandatory    },
    ...
}

MultipleULAoA ::= SEQUENCE {
    multipleULAoA                     MultipleULAoA-List,
    iE-Extensions                     ProtocolExtensionContainer { { MultipleULAoA-ExtIEs} } OPTIONAL,
    ...
}

MultipleULAoA-ExtIEs NRPPA-PROTOCOL-EXTENSION ::= {
    ...
}

MultipleULAoA-List ::= SEQUENCE (SIZE(1.. maxnoofULAoAs)) OF MultipleULAoA-Item

MultipleULAoA-Item ::= CHOICE {
    uL-AoA      UL-AoA,
    ul-ZoA      ZoA,
    choice-extension ProtocolIE-Single-Container { { MultipleULAoA-Item-ExtIEs } }
}

MultipleULAoA-Item-ExtIEs NRPPA-PROTOCOL-IES ::= {
    ...
}


-- N

NarrowBandIndex ::= INTEGER (0..15,...)

NG-RANAccessPointPosition ::= SEQUENCE {
    latitudeSign                ENUMERATED {north, south},
    latitude                    INTEGER (0..8388607),
    longitude                   INTEGER (-8388608..8388607),
    directionOfAltitude         ENUMERATED {height, depth},
    altitude                    INTEGER (0..32767),
    uncertaintySemi-major       INTEGER (0..127),
    uncertaintySemi-minor       INTEGER (0..127),
    orientationOfMajorAxis      INTEGER (0..179),
    uncertaintyAltitude         INTEGER (0..127),
    confidence                  INTEGER (0..100),
    iE-Extensions               ProtocolExtensionContainer { { NG-RANAccessPointPosition-ExtIEs} } OPTIONAL,
    ...
}

NG-RANAccessPointPosition-ExtIEs NRPPA-PROTOCOL-EXTENSION ::= {




    ...
}

NGRANHighAccuracyAccessPointPosition ::= SEQUENCE {
    latitude                    INTEGER (-2147483648.. 2147483647),
    longitude                   INTEGER (-2147483648.. 2147483647),
    altitude                    INTEGER (-64000..1280000),
    uncertaintySemi-major       INTEGER (0..255),
    uncertaintySemi-minor       INTEGER (0..255),
    orientationOfMajorAxis      INTEGER (0..179),
    horizontalConfidence        INTEGER (0..100),
    uncertaintyAltitude         INTEGER (0..255),
    verticalConfidence          INTEGER (0..100),
    iE-Extensions               ProtocolExtensionContainer { { NGRANHighAccuracyAccessPointPosition-ExtIEs} } OPTIONAL,
    ...
}

NGRANHighAccuracyAccessPointPosition-ExtIEs NRPPA-PROTOCOL-EXTENSION ::= {
    ...
}

NG-RAN-CGI ::= SEQUENCE {
    pLMN-Identity               PLMN-Identity,
    nG-RANcell      NG-RANCell,
    iE-Extensions               ProtocolExtensionContainer { {NG-RAN-CGI-ExtIEs} } OPTIONAL,
    ...
}

NG-RAN-CGI-ExtIEs NRPPA-PROTOCOL-EXTENSION ::= {
    ...
}

NG-RANCell ::= CHOICE {
    eUTRA-CellID    EUTRACellIdentifier,
    nR-CellID       NRCellIdentifier,
    choice-Extension            ProtocolIE-Single-Container {{ NG-RANCell-ExtensionIE }}
}

NG-RANCell-ExtensionIE NRPPA-PROTOCOL-IES ::= {
    ...
}

NR-ARFCN ::= INTEGER (0..3279165)

NRCellIdentifier ::= BIT STRING (SIZE (36))

NR-PCI ::= INTEGER (0..1007)

NR-PRS-Beam-Information ::= SEQUENCE {
    nR-PRS-Beam-InformationList SEQUENCE (SIZE(1.. maxPRS-ResourceSets)) OF NR-PRS-Beam-InformationItem,
    lCS-to-GCS-TranslationList SEQUENCE (SIZE(1..maxnolcs-gcs-translation)) OF LCS-to-GCS-TranslationItem    OPTIONAL,
    iE-Extensions   ProtocolExtensionContainer { { NR-PRS-Beam-Information-IEs} } OPTIONAL,
    ...
}





NR-PRS-Beam-Information-IEs NRPPA-PROTOCOL-EXTENSION ::= {
 ...
}

NR-PRS-Beam-InformationItem ::= SEQUENCE {
    pRSresourceSetID    PRS-Resource-Set-ID,
    pRSAngle        SEQUENCE (SIZE(1..maxPRS-ResourcesPerSet)) OF PRSAngleItem,
    iE-Extensions   ProtocolExtensionContainer { { NR-PRS-Beam-InformationItem-ExtIEs} } OPTIONAL,
    ...
}

NR-PRS-Beam-InformationItem-ExtIEs NRPPA-PROTOCOL-EXTENSION ::= {
 ...
}

NR-TADV ::= INTEGER (0.. 7690)

NumberOfAntennaPorts-EUTRA ::= ENUMERATED {
        n1-or-n2,
        n4,
        ...
}

NumberOfDlFrames-EUTRA ::= ENUMERATED {
        sf1,
        sf2,
        sf4,
        sf6,
        ...
}

NumberOfDlFrames-Extended-EUTRA ::= INTEGER (1..160,...)

NumberOfFrequencyHoppingBands ::= ENUMERATED {
    twobands,
    fourbands,
    ...
}

NumberOfTRPRxTEG ::= ENUMERATED {two, three, four, six, eight, ...}

NumberOfTRPRxTxTEG ::= ENUMERATED {two, three, four, six, eight, ...}

NZP-CSI-RS-ResourceID::= INTEGER    (0..191)

-- O

OnDemandPRS-Info ::= SEQUENCE {
    onDemandPRSRequestAllowed                  BIT STRING (SIZE (16)),
    allowedResourceSetPeriodicityValues        BIT STRING (SIZE (24)) OPTIONAL,
    allowedPRSBandwidthValues                  BIT STRING (SIZE (64)) OPTIONAL,
    allowedResourceRepetitionFactorValues      BIT STRING (SIZE (8))   OPTIONAL,
    allowedResourceNumberOfSymbolsValues       BIT STRING (SIZE (8))   OPTIONAL,




    allowedCombSizeValues                   BIT STRING (SIZE (8))   OPTIONAL,
    iE-Extensions   ProtocolExtensionContainer { { OnDemandPRS-Info-ExtIEs} } OPTIONAL,
    ...
}

OnDemandPRS-Info-ExtIEs NRPPA-PROTOCOL-EXTENSION ::= {
    ...
}

OTDOACells ::= SEQUENCE (SIZE (1.. maxCellinRANnode)) OF SEQUENCE {
    oTDOACellInfo                   OTDOACell-Information,
    iE-Extensions                   ProtocolExtensionContainer { {OTDOACells-ExtIEs} } OPTIONAL,
    ...
}

OTDOACells-ExtIEs NRPPA-PROTOCOL-EXTENSION ::= {
    ...
}

OTDOACell-Information ::= SEQUENCE (SIZE (1..maxnoOTDOAtypes)) OF OTDOACell-Information-Item

OTDOACell-Information-Item ::= CHOICE {
    pCI-EUTRA                                   PCI-EUTRA,
    cGI-EUTRA                                   CGI-EUTRA,
    tAC                                         TAC,
    eARFCN                                      EARFCN,
    pRS-Bandwidth-EUTRA                         PRS-Bandwidth-EUTRA,
    pRS-ConfigurationIndex-EUTRA                PRS-ConfigurationIndex-EUTRA,
    cPLength-EUTRA                              CPLength-EUTRA,
    numberOfDlFrames-EUTRA                      NumberOfDlFrames-EUTRA,
    numberOfAntennaPorts-EUTRA                  NumberOfAntennaPorts-EUTRA,
    sFNInitialisationTime-EUTRA                 SFNInitialisationTime-EUTRA,
    nG-RANAccessPointPosition                   NG-RANAccessPointPosition,
    pRSMutingConfiguration-EUTRA                PRSMutingConfiguration-EUTRA,
    prsid-EUTRA                                 PRS-ID-EUTRA,
    tpid-EUTRA                                  TP-ID-EUTRA,
    tpType-EUTRA                                TP-Type-EUTRA,
    numberOfDlFrames-Extended-EUTRA             NumberOfDlFrames-Extended-EUTRA,
    crsCPlength-EUTRA                           CPLength-EUTRA,
    dL-Bandwidth-EUTRA                          DL-Bandwidth-EUTRA,
    pRSOccasionGroup-EUTRA                      PRSOccasionGroup-EUTRA,
    pRSFrequencyHoppingConfiguration-EUTRA      PRSFrequencyHoppingConfiguration-EUTRA,
    choice-Extension        ProtocolIE-Single-Container {{ OTDOACell-Information-Item-ExtensionIE }}
}

OTDOACell-Information-Item-ExtensionIE NRPPA-PROTOCOL-IES ::= {
    { ID id-TDD-Config-EUTRA-Item       CRITICALITY     ignore TYPE    TDD-Config-EUTRA-Item       PRESENCE   mandatory }|
    { ID id-CGI-NR                      CRITICALITY     ignore TYPE    CGI-NR                      PRESENCE   mandatory }|
    { ID id-SFNInitialisationTime-NR    CRITICALITY     ignore TYPE    SFNInitialisationTime-EUTRA PRESENCE   mandatory },
    ...
}

OTDOA-Information-Item ::= ENUMERATED {
        pci,




        cGI,
        tac,
        earfcn,
        prsBandwidth,
        prsConfigIndex,
        cpLength,
        noDlFrames,
        noAntennaPorts,
        sFNInitTime,
        nG-RANAccessPointPosition,
        prsmutingconfiguration,
        prsid,
        tpid,
        tpType,
        crsCPlength,
        dlBandwidth,
        multipleprsConfigurationsperCell,
        prsOccasionGroup,
        prsFrequencyHoppingConfiguration,
        ...,
        tddConfig
}

OtherRATMeasurementQuantities ::= SEQUENCE (SIZE (0.. maxNoMeas)) OF ProtocolIE-Single-Container { {OtherRATMeasurementQuantities-ItemIEs} }

OtherRATMeasurementQuantities-ItemIEs NRPPA-PROTOCOL-IES ::= {
    { ID id-OtherRATMeasurementQuantities-Item CRITICALITY reject   TYPE OtherRATMeasurementQuantities-Item PRESENCE mandatory}}

OtherRATMeasurementQuantities-Item ::= SEQUENCE {
    otherRATMeasurementQuantitiesValue          OtherRATMeasurementQuantitiesValue,
    iE-Extensions                               ProtocolExtensionContainer { { OtherRATMeasurementQuantitiesValue-ExtIEs} } OPTIONAL,
    ...
}

OtherRATMeasurementQuantitiesValue-ExtIEs NRPPA-PROTOCOL-EXTENSION ::= {
    ...
}

OtherRATMeasurementQuantitiesValue ::= ENUMERATED {
    geran,
    utran,
    ... ,
    nR,
    eUTRA
}

OtherRATMeasurementResult ::= SEQUENCE (SIZE (1.. maxNoMeas)) OF OtherRATMeasuredResultsValue

OtherRATMeasuredResultsValue ::= CHOICE {
    resultGERAN                                 ResultGERAN,
    resultUTRAN                                 ResultUTRAN,
    choice-Extension        ProtocolIE-Single-Container {{ OtherRATMeasuredResultsValue-ExtensionIE }}
}






OtherRATMeasuredResultsValue-ExtensionIE NRPPA-PROTOCOL-IES ::= {
    { ID id-ResultNR        CRITICALITY     ignore TYPE     ResultNR             PRESENCE   mandatory }|
    { ID id-ResultEUTRA     CRITICALITY     ignore TYPE     ResultEUTRA          PRESENCE   mandatory },
    ...
}

Outcome ::= ENUMERATED {
        failed,
        ...
}


-- P

PathlossReferenceInformation ::= SEQUENCE {
    pathlossReferenceSignal                 PathlossReferenceSignal,
    iE-Extensions                   ProtocolExtensionContainer { { PathlossReferenceInformation-ExtIEs } } OPTIONAL,
    ...
}

PathlossReferenceInformation-ExtIEs NRPPA-PROTOCOL-EXTENSION ::= {
    ...
}


PathlossReferenceSignal ::= CHOICE {
    sSB-Reference                   SSB,
    dL-PRS-Reference                DL-PRS,
    choice-Extension                ProtocolIE-Single-Container {{ PathlossReferenceSignal-ExtensionIE }}
}

PathlossReferenceSignal-ExtensionIE NRPPA-PROTOCOL-IES ::= {
    ...
}


PCI-EUTRA ::= INTEGER (0..503, ...)

PhysCellIDGERAN ::= INTEGER (0..63, ...)

PhysCellIDUTRA-FDD ::= INTEGER (0..511, ...)

PhysCellIDUTRA-TDD ::= INTEGER (0..127, ...)

PLMN-Identity ::= OCTET STRING (SIZE(3))

PeriodicityList ::= SEQUENCE (SIZE (1.. maxnoSRS-ResourcePerSet)) OF PeriodicityItem

PeriodicityItem ::= ENUMERATED {ms0dot125, ms0dot25, ms0dot5, ms0dot625, ms1, ms1dot25, ms2, ms2dot5, ms4dot, ms5, ms8, ms10, ms16, ms20, ms32,
ms40, ms64, ms80m, ms160, ms320, ms640m, ms1280, ms2560, ms5120, ms10240, ...}


PosSIBs ::= SEQUENCE (SIZE (1.. maxNrOfPosSIBs)) OF SEQUENCE {




    posSIB-Type                       PosSIB-Type,
    posSIB-Segments                   PosSIB-Segments,
    assistanceInformationMetaData     AssistanceInformationMetaData   OPTIONAL,
    broadcastPriority                 INTEGER (1..16,...)             OPTIONAL,
    iE-Extensions                     ProtocolExtensionContainer { { PosSIBs-ExtIEs} }   OPTIONAL,
    ...
}

PosSIBs-ExtIEs NRPPA-PROTOCOL-EXTENSION ::= {
    ...
}

PosSIB-Segments ::= SEQUENCE (SIZE (1.. maxNrOfSegments)) OF SEQUENCE {
    assistanceDataSIBelement            OCTET STRING,
    iE-Extensions                       ProtocolExtensionContainer { { PosSIB-Segments-ExtIEs} } OPTIONAL,
    ...
}

PosSIB-Segments-ExtIEs NRPPA-PROTOCOL-EXTENSION ::= {
    ...
}

PosSIB-Type ::= ENUMERATED {
    posSibType1-1,
    posSibType1-2,
    posSibType1-3,
    posSibType1-4,
    posSibType1-5,
    posSibType1-6,
    posSibType1-7,
    posSibType1-8,
    posSibType2-1,
    posSibType2-2,
    posSibType2-3,
    posSibType2-4,
    posSibType2-5,
    posSibType2-6,
    posSibType2-7,
    posSibType2-8,
    posSibType2-9,
    posSibType2-10,
    posSibType2-11,
    posSibType2-12,
    posSibType2-13,
    posSibType2-14,
    posSibType2-15,
    posSibType2-16,
    posSibType2-17,
    posSibType2-18,
    posSibType2-19,
    posSibType2-20,
    posSibType2-21,
    posSibType2-22,
    posSibType2-23,




    posSibType2-24,
    posSibType2-25,
    posSibType3-1,
    posSibType4-1,
    posSibType5-1,
    posSibType6-1,
    posSibType6-2,
    posSibType6-3,
    ...,
    posSibType1-9,
    posSibType1-10,
    posSibType6-4,
    posSibType6-5,
    posSibType6-6
}

PosSRSResource-List ::= SEQUENCE (SIZE (1..maxnoSRS-PosResources)) OF PosSRSResource-Item

PosSRSResource-Item ::= SEQUENCE {
    srs-PosResourceId               SRSPosResourceID,
    transmissionCombPos             TransmissionCombPos,
    startPosition                   INTEGER (0..13),
    nrofSymbols                     ENUMERATED {n1, n2, n4, n8, n12},
    freqDomainShift                 INTEGER (0..268),
    c-SRS                           INTEGER (0..63),
    groupOrSequenceHopping          ENUMERATED { neither, groupHopping, sequenceHopping },
    resourceTypePos                 ResourceTypePos,
    sequenceId                      INTEGER (0.. 65535),
    spatialRelationPos              SpatialRelationPos OPTIONAL,
    iE-Extensions       ProtocolExtensionContainer { { PosSRSResource-Item-ExtIEs} }    OPTIONAL,
    ...
}

PosSRSResource-Item-ExtIEs NRPPA-PROTOCOL-EXTENSION ::= {
    ...
}


PosSRSResourceID-List ::= SEQUENCE (SIZE (1..maxnoSRS-PosResources)) OF SRSPosResourceID

PosSRSResourceSet-List ::= SEQUENCE (SIZE (1..maxnoSRS-PosResourceSets)) OF PosSRSResourceSet-Item

PosSRSResourceIDPerSet-List ::= SEQUENCE (SIZE (1..maxnoSRS-PosResourcePerSet)) OF SRSPosResourceID


PosSRSResourceSet-Item ::= SEQUENCE {
    possrsResourceSetID             INTEGER(0..15),
    possRSResourceIDPerSet-List     PosSRSResourceIDPerSet-List,
    posresourceSetType              PosResourceSetType,
    iE-Extensions       ProtocolExtensionContainer { { PosSRSResourceSet-Item-ExtIEs} } OPTIONAL,
    ...
}

PosSRSResourceSet-Item-ExtIEs NRPPA-PROTOCOL-EXTENSION ::= {




    ...
}

PosResourceSetType ::= CHOICE {
    periodic           PosResourceSetTypePeriodic,
    semi-persistent    PosResourceSetTypeSemi-persistent,
    aperiodic          PosResourceSetTypeAperiodic,
    choice-extension               ProtocolIE-Single-Container {{ PosResourceSetType-ExtIEs }}
}

PosResourceSetType-ExtIEs NRPPA-PROTOCOL-IES ::= {
    ...
}

PosResourceSetTypePeriodic ::= SEQUENCE {
    posperiodicSet          ENUMERATED{true, ...},
    iE-Extensions       ProtocolExtensionContainer { { PosResourceSetTypePeriodic-ExtIEs} } OPTIONAL,
    ...
}

PosResourceSetTypePeriodic-ExtIEs NRPPA-PROTOCOL-EXTENSION ::= {
    ...
}

PosResourceSetTypeSemi-persistent ::= SEQUENCE {
possemi-persistentSet   ENUMERATED{true, ...},
    iE-Extensions       ProtocolExtensionContainer { { PosResourceSetTypeSemi-persistent-ExtIEs} }   OPTIONAL,
    ...
}

PosResourceSetTypeSemi-persistent-ExtIEs NRPPA-PROTOCOL-EXTENSION ::= {
    ...
}

PosResourceSetTypeAperiodic ::= SEQUENCE {
    sRSResourceTrigger          INTEGER(1..3),
    iE-Extensions               ProtocolExtensionContainer { { PosResourceSetTypeAperiodic-ExtIEs} } OPTIONAL,
    ...
}

PosResourceSetTypeAperiodic-ExtIEs NRPPA-PROTOCOL-EXTENSION ::= {
    ...
}

PreconfigurationResult ::= BIT STRING (SIZE(8))

PRS-Bandwidth-EUTRA ::= ENUMERATED {
        bw6,
        bw15,
        bw25,
        bw50,
        bw75,
        bw100,
        ...




}


PRSAngleItem ::= SEQUENCE {
    nRPRSAzimuth           INTEGER (0..359),
    nRPRSAzimuthFine       INTEGER (0..9) OPTIONAL,
    nRPRSElevation         INTEGER (0..180) OPTIONAL,
    nRPRSElevationFine     INTEGER (0..9) OPTIONAL,
    iE-Extensions          ProtocolExtensionContainer { { PRSAngleItem-ExtIEs} } OPTIONAL,
    ...
}

PRSAngleItem-ExtIEs NRPPA-PROTOCOL-EXTENSION ::= {
    { ID id-PRS-Resource-ID     CRITICALITY ignore EXTENSION PRS-Resource-ID         PRESENCE optional },
    ...
}

PRSInformationPos ::= SEQUENCE {
    pRS-IDPos                  INTEGER(0..255),
    pRS-Resource-Set-IDPos     INTEGER(0..7),
    pRS-Resource-IDPos         INTEGER(0..63) OPTIONAL,
    iE-Extensions                  ProtocolExtensionContainer { { PRSInformationPos-ExtIEs} } OPTIONAL,
    ...
}

PRSInformationPos-ExtIEs NRPPA-PROTOCOL-EXTENSION ::= {
    ...
}

PRSConfigRequestType ::= ENUMERATED {configure, off, ...}

PRSConfiguration ::= SEQUENCE {
    pRSResourceSet-List               PRSResourceSet-List,
    iE-Extensions                     ProtocolExtensionContainer { { PRSConfiguration-ExtIEs} } OPTIONAL,
    ...
}

PRSConfiguration-ExtIEs NRPPA-PROTOCOL-EXTENSION ::= {
    ...
}


PRS-ConfigurationIndex-EUTRA ::= INTEGER (0..4095, ...)

PRS-ID-EUTRA     ::= INTEGER (0..4095, ...)

PRSMutingConfiguration-EUTRA ::= CHOICE {
    two                                                   BIT STRING (SIZE (2)),
    four                                                  BIT STRING (SIZE (4)),
    eight                                                 BIT STRING (SIZE (8)),
    sixteen                                               BIT STRING (SIZE (16)),
    thirty-two                                            BIT STRING (SIZE (32)),
    sixty-four                                            BIT STRING (SIZE (64)),
    one-hundred-and-twenty-eight                          BIT STRING (SIZE (128)),




    two-hundred-and-fifty-six                           BIT STRING (SIZE (256)),
    five-hundred-and-twelve                             BIT STRING (SIZE (512)),
    one-thousand-and-twenty-four                        BIT STRING (SIZE (1024)),
    choice-Extension            ProtocolIE-Single-Container {{ PRSMutingConfiguration-EUTRA-ExtensionIE }}
}

PRSMutingConfiguration-EUTRA-ExtensionIE NRPPA-PROTOCOL-IES ::= {
    ...
}

PRSOccasionGroup-EUTRA ::= ENUMERATED {
    og2,
    og4,
    og8,
    og16,
    og32,
    og64,
    og128,
    ...
}

PRSFrequencyHoppingConfiguration-EUTRA ::= SEQUENCE {
    noOfFreqHoppingBands        NumberOfFrequencyHoppingBands,
    bandPositions               SEQUENCE(SIZE (1..maxnoFreqHoppingBandsMinusOne)) OF NarrowBandIndex,
    iE-Extensions               ProtocolExtensionContainer { { PRSFrequencyHoppingConfiguration-EUTRA-Item-IEs} } OPTIONAL,
    ...
}

PRSFrequencyHoppingConfiguration-EUTRA-Item-IEs NRPPA-PROTOCOL-EXTENSION ::= {
    ...
}

PRS-Measurements-Info-List ::= SEQUENCE (SIZE(1..maxFreqLayers)) OF PRS-Measurements-Info-List-Item

PRS-Measurements-Info-List-Item ::= SEQUENCE {
    pointA                      INTEGER (0..3279165),
    measPRSPeriodicity          ENUMERATED {ms20, ms40, ms80, ms160, ...},
    measPRSOffset               INTEGER (0..159, ...),
    measurementPRSLength        ENUMERATED {ms1dot5, ms3, ms3dot5, ms4, ms5dot5, ms6, ms10, ms20},
    iE-Extensions   ProtocolExtensionContainer { { PRS-Measurements-Info-List-Item-ExtIEs} } OPTIONAL,
        ...
}

PRS-Measurements-Info-List-Item-ExtIEs NRPPA-PROTOCOL-EXTENSION ::= {
    ...
}


PRSMuting::= SEQUENCE {
    pRSMutingOption1              PRSMutingOption1        OPTIONAL,
    pRSMutingOption2              PRSMutingOption2        OPTIONAL,
    iE-Extensions                     ProtocolExtensionContainer { { PRSMuting-ExtIEs} } OPTIONAL,
    ...
}




PRSMuting-ExtIEs NRPPA-PROTOCOL-EXTENSION ::= {
    ...
}


PRSMutingOption1 ::= SEQUENCE {
    mutingPattern                       DL-PRSMutingPattern,
    mutingBitRepetitionFactor           ENUMERATED{n1,n2,n4,n8,...},
    iE-Extensions                   ProtocolExtensionContainer { { PRSMutingOption1-ExtIEs} } OPTIONAL,
    ...
}
PRSMutingOption1-ExtIEs NRPPA-PROTOCOL-EXTENSION ::= {
    ...
}

PRSMutingOption2 ::= SEQUENCE {
    mutingPattern                       DL-PRSMutingPattern,
    iE-Extensions                   ProtocolExtensionContainer { { PRSMutingOption2-ExtIEs} } OPTIONAL,
    ...
}
PRSMutingOption2-ExtIEs NRPPA-PROTOCOL-EXTENSION ::= {
    ...
}

PRSResource-List::= SEQUENCE (SIZE (1..maxnoofPRSresource)) OF PRSResource-Item

PRSResource-Item ::= SEQUENCE {
    pRSResourceID           PRS-Resource-ID,
    sequenceID              INTEGER(0..4095),
    rEOffset                INTEGER(0..11,...),
    resourceSlotOffset      INTEGER(0..511),
    resourceSymbolOffset    INTEGER(0..12),
    qCLInfo                 PRSResource-QCLInfo     OPTIONAL,
    iE-Extensions                   ProtocolExtensionContainer { { PRSResource-Item-ExtIEs} } OPTIONAL,
    ...
}
PRSResource-Item-ExtIEs NRPPA-PROTOCOL-EXTENSION ::= {
    ...
}

PRSResource-QCLInfo ::= CHOICE {
    qCLSourceSSB       PRSResource-QCLSourceSSB,
    qCLSourcePRS       PRSResource-QCLSourcePRS,
    choice-Extension       ProtocolIE-Single-Container {{ PRSResource-QCLInfo-ExtIEs }}
}

PRSResource-QCLInfo-ExtIEs NRPPA-PROTOCOL-IES ::= {
    ...
}

PRSResource-QCLSourceSSB ::= SEQUENCE {
    pCI-NR              INTEGER(0..1007),
    sSB-Index           SSB-Index    OPTIONAL,
    iE-Extensions       ProtocolExtensionContainer { { PRSResource-QCLSourceSSB-ExtIEs} } OPTIONAL,




    ...
}

PRSResource-QCLSourceSSB-ExtIEs NRPPA-PROTOCOL-EXTENSION ::= {
    ...
}

PRSResource-QCLSourcePRS ::= SEQUENCE {
    qCLSourcePRSResourceSetID       PRS-Resource-Set-ID,
    qCLSourcePRSResourceID          PRS-Resource-ID OPTIONAL,
    iE-Extensions                   ProtocolExtensionContainer { { PRSResource-QCLSourcePRS-ExtIEs} } OPTIONAL,
    ...
}
PRSResource-QCLSourcePRS-ExtIEs NRPPA-PROTOCOL-EXTENSION ::= {
    ...
}



PRSResourceSet-List ::= SEQUENCE (SIZE (1..maxnoofPRSresourceSet)) OF PRSResourceSet-Item

PRSResourceSet-Item ::= SEQUENCE {
    pRSResourceSetID                  PRS-Resource-Set-ID,
    subcarrierSpacing                 ENUMERATED{kHz15, kHz30, kHz60, kHz120, ...},
    pRSbandwidth                      INTEGER(1..63),
    startPRB                          INTEGER(0..2176),
    pointA                            INTEGER (0..3279165),
    combSize                          ENUMERATED{n2, n4, n6, n12, ...},
    cPType                            ENUMERATED{normal, extended, ...},
    resourceSetPeriodicity            ENUMERATED{n4,n5,n8,n10,n16,n20,n32,n40,n64,n80,n160,n320,n640,n1280,n2560,n5120,n10240,n20480,n40960,
n81920,...},
    resourceSetSlotOffset             INTEGER(0..81919,...),
    resourceRepetitionFactor          ENUMERATED{rf1,rf2,rf4,rf6,rf8,rf16,rf32,...},
    resourceTimeGap                   ENUMERATED{tg1,tg2,tg4,tg8,tg16,tg32,...},
    resourceNumberofSymbols           ENUMERATED{n2,n4,n6,n12,...},
    pRSMuting                         PRSMuting       OPTIONAL,
    pRSResourceTransmitPower          INTEGER(-60..50),
    pRSResource-List                  PRSResource-List,
    iE-Extensions                     ProtocolExtensionContainer { { PRSResourceSet-Item-ExtIEs} } OPTIONAL,
    ...
}

PRSResourceSet-Item-ExtIEs NRPPA-PROTOCOL-EXTENSION ::= {
    ...
}

PRS-Resource-ID ::= INTEGER (0..63)

PRS-Resource-Set-ID ::= INTEGER(0..7)

PRS-ID ::= INTEGER(0..255)

PRSTransmissionOffIndication ::= CHOICE {
    pRSTransmissionOffPerTRP                 NULL,




    pRSTransmissionOffPerResourceSet        PRSTransmissionOffPerResourceSet,
    pRSTransmissionOffPerResource           PRSTransmissionOffPerResource,
    choice-Extension        ProtocolIE-Single-Container {{ PRSTransmissionOffIndication-ExtIEs }}
}

PRSTransmissionOffIndication-ExtIEs NRPPA-PROTOCOL-IES ::= {
    ...
}

PRSTransmissionOffPerResource ::= SEQUENCE (SIZE (1..maxnoofPRSresourceSet)) OF PRSTransmissionOffPerResource-Item

PRSTransmissionOffPerResource-Item ::= SEQUENCE {
    pRSResourceSetID                                PRS-Resource-Set-ID,
    pRSTransmissionOffIndicationPerResourceList     SEQUENCE (SIZE(1.. maxnoofPRSresource)) OF PRSTransmissionOffIndicationPerResource-Item,
    iE-Extensions       ProtocolExtensionContainer { { PRSTransmissionOffPerResource-Item-ExtIEs} } OPTIONAL,
    ...
}

PRSTransmissionOffPerResource-Item-ExtIEs NRPPA-PROTOCOL-EXTENSION ::= {
    ...
}

PRSTransmissionOffIndicationPerResource-Item ::= SEQUENCE {
    pRSResourceID       PRS-Resource-ID,
    iE-Extensions       ProtocolExtensionContainer { { PRSTransmissionOffIndicationPerResource-Item-ExtIEs} } OPTIONAL,
    ...
}

PRSTransmissionOffIndicationPerResource-Item-ExtIEs NRPPA-PROTOCOL-EXTENSION ::= {
    ...
}

PRSTransmissionOffInformation ::= SEQUENCE {
    pRSTransmissionOffIndication    PRSTransmissionOffIndication,
    iE-Extensions                   ProtocolExtensionContainer { { PRSTransmissionOffInformation-ExtIEs} } OPTIONAL,
    ...
}

PRSTransmissionOffInformation-ExtIEs NRPPA-PROTOCOL-EXTENSION ::= {
    ...
}

PRSTransmissionOffPerResourceSet ::= SEQUENCE (SIZE (1..maxnoofPRSresourceSet)) OF PRSTransmissionOffPerResourceSet-Item

PRSTransmissionOffPerResourceSet-Item ::= SEQUENCE {
    pRSResourceSetID        PRS-Resource-Set-ID,
    iE-Extensions           ProtocolExtensionContainer { { PRSTransmissionOffPerResourceSet-Item-ExtIEs} } OPTIONAL,
    ...
}

PRSTransmissionOffPerResourceSet-Item-ExtIEs NRPPA-PROTOCOL-EXTENSION ::= {
    ...
}





PRSTRPList ::= SEQUENCE (SIZE(1.. maxnoTRPs)) OF PRSTRPItem

PRSTRPItem ::= SEQUENCE {
        tRP-ID      TRP-ID,
        requestedDLPRSTransmissionCharacteristics   RequestedDLPRSTransmissionCharacteristics    OPTIONAL,
-- The IE shall be present if the PRS Configuration Request Type IE is set to “configure” --
        pRSTransmissionOffInformation               PRSTransmissionOffInformation                OPTIONAL,
-- The IE shall be present if the PRS Configuration Request Type IE is set to “off” --
        iE-Extensions   ProtocolExtensionContainer { { PRSTRPItem-ExtIEs} } OPTIONAL,
        ...
}

PRSTRPItem-ExtIEs NRPPA-PROTOCOL-EXTENSION ::= {
    ...
}



PRSTransmissionTRPList ::= SEQUENCE (SIZE(1.. maxnoTRPs)) OF PRSTransmissionTRPItem

PRSTransmissionTRPItem ::= SEQUENCE {
        tRP-ID              TRP-ID,
        pRSConfiguration    PRSConfiguration,
    iE-Extensions   ProtocolExtensionContainer { { PRSTransmissionTRPItem-ExtIEs} } OPTIONAL,
        ...
}

PRSTransmissionTRPItem-ExtIEs NRPPA-PROTOCOL-EXTENSION ::= {
    ...
}


-- Q

-- R

ReferenceSignal ::= CHOICE {
    nZP-CSI-RS                                NZP-CSI-RS-ResourceID,
    sSB                                       SSB,
    sRS                                       SRSResourceID,
    positioningSRS                            SRSPosResourceID,
    dL-PRS                                    DL-PRS,
    choice-Extension                  ProtocolIE-Single-Container {{ReferenceSignal-ExtensionIE }}
}

ReferenceSignal-ExtensionIE NRPPA-PROTOCOL-IES ::= {
    ...
}

ReferencePoint ::= CHOICE {
    relativeCoordinateID              CoordinateID,
    referencePointCoordinate          NG-RANAccessPointPosition,
    referencePointCoordinateHA        NGRANHighAccuracyAccessPointPosition,
    choice-Extension                  ProtocolIE-Single-Container { { ReferencePoint-ExtIEs} }




}

ReferencePoint-ExtIEs NRPPA-PROTOCOL-IES ::= {
    ...
}

CoordinateID ::= INTEGER (0..511, ...)
RelativeGeodeticLocation ::= SEQUENCE {
    milli-Arc-SecondUnits       ENUMERATED {zerodot03, zerodot3, three, ...},   heightUnits             ENUMERATED {mm, cm, m, ...},
    deltaLatitude               INTEGER (-1024.. 1023),
    deltaLongitude              INTEGER (-1024.. 1023),
    deltaHeight                 INTEGER (-1024.. 1023),
    locationUncertainty         LocationUncertainty,
    iE-extensions                       ProtocolExtensionContainer {{RelativeGeodeticLocation-ExtIEs }} OPTIONAL,
    ...
}

RelativeGeodeticLocation-ExtIEs NRPPA-PROTOCOL-EXTENSION ::= {
    ...
}


RelativeCartesianLocation ::= SEQUENCE {
    xYZunit                     ENUMERATED {mm, cm, dm, ...},
    xvalue                      INTEGER (-65536..65535),
    yvalue                      INTEGER (-65536..65535),
    zvalue                      INTEGER (-32768..32767),
    locationUncertainty         LocationUncertainty,
    iE-Extensions               ProtocolExtensionContainer { { RelativeCartesianLocation-ExtIEs} } OPTIONAL,
    ...
}

RelativeCartesianLocation-ExtIEs NRPPA-PROTOCOL-EXTENSION ::= {
    ...
}

RelativePathDelay ::= CHOICE {
    k0          INTEGER(0..16351),
    k1          INTEGER(0..8176),
    k2          INTEGER(0..4088),
    k3      INTEGER(0..2044),
    k4          INTEGER(0..1022),
    k5          INTEGER(0..511),
    choice-Extension        ProtocolIE-Single-Container { { RelativePathDelay-ExtIEs} }
}

RelativePathDelay-ExtIEs NRPPA-PROTOCOL-IES ::= {
    ...
}

ReportCharacteristics ::= ENUMERATED {
    onDemand,
    periodic,
    ...




}

RequestedDLPRSTransmissionCharacteristics ::= SEQUENCE {
    requestedDLPRSResourceSet-List      RequestedDLPRSResourceSet-List,
    numberofFrequencyLayers             INTEGER(1..4)           OPTIONAL,
    startTimeAndDuration                StartTimeAndDuration    OPTIONAL,
    iE-Extensions   ProtocolExtensionContainer { { RequestedDLPRSTransmissionCharacteristics-ExtIEs} } OPTIONAL,
    ...
}

RequestedDLPRSTransmissionCharacteristics-ExtIEs NRPPA-PROTOCOL-EXTENSION ::= {
    ...
}

RequestedDLPRSResourceSet-List ::= SEQUENCE (SIZE (1..maxnoofPRSresourceSet)) OF RequestedDLPRSResourceSet-Item

RequestedDLPRSResourceSet-Item ::= SEQUENCE {
    pRSbandwidth                    INTEGER(1..63) OPTIONAL,
    combSize                        ENUMERATED{n2, n4, n6, n12, ...}    OPTIONAL,
    resourceSetPeriodicity          ENUMERATED{n4,n5,n8,n10,n16,n20,n32,n40,n64,n80,n160,n320,n640,n1280,n2560,n5120,n10240,n20480,n40960,
n81920,...} OPTIONAL,
    resourceRepetitionFactor        ENUMERATED{rf1,rf2,rf4,rf6,rf8,rf16,rf32,...}       OPTIONAL,
    resourceNumberofSymbols         ENUMERATED{n2,n4,n6,n12,...}                        OPTIONAL,
    requestedDLPRSResource-List     RequestedDLPRSResource-List         OPTIONAL,
    resourceSetStartTimeAndDuration StartTimeAndDuration            OPTIONAL,
    iE-Extensions                   ProtocolExtensionContainer { { RequestedDLPRSResourceSet-Item-ExtIEs} } OPTIONAL,
    ...
}

RequestedDLPRSResourceSet-Item-ExtIEs NRPPA-PROTOCOL-EXTENSION ::= {
    ...
}

RequestedDLPRSResource-List::= SEQUENCE (SIZE (1..maxnoofPRSresource)) OF RequestedDLPRSResource-Item

RequestedDLPRSResource-Item ::= SEQUENCE {
    qCLInfo                PRSResource-QCLInfo     OPTIONAL,
    iE-Extensions          ProtocolExtensionContainer { { RequestedDLPRSResource-Item-ExtIEs} } OPTIONAL,
    ...
}

RequestedDLPRSResource-Item-ExtIEs NRPPA-PROTOCOL-EXTENSION ::= {
    ...
}


RequestedSRSTransmissionCharacteristics ::= SEQUENCE {
    numberOfTransmissions   INTEGER (0..500,...)                            OPTIONAL,
-- The IE shall be present if the Resource Type IE is set to “periodic” --
    resourceType            ENUMERATED {periodic, semi-persistent, aperiodic, ...},
    bandwidth               BandwidthSRS,
    listOfSRSResourceSet    SEQUENCE (SIZE (1.. maxnoSRS-ResourceSets)) OF SRSResourceSet-Item OPTIONAL,
    sSBInformation          SSBInfo     OPTIONAL,
    iE-Extensions           ProtocolExtensionContainer { { RequestedSRSTransmissionCharacteristics-ExtIEs} } OPTIONAL,




    ...
}

RequestedSRSTransmissionCharacteristics-ExtIEs NRPPA-PROTOCOL-EXTENSION ::= {
    { ID id-SrsFrequency        CRITICALITY ignore EXTENSION SrsFrequency       PRESENCE optional },
    ...
}


SRSResourceSet-Item ::= SEQUENCE {
    numberOfSRSResourcePerSet       INTEGER (1..16, ...)            OPTIONAL,
    periodicityList                 PeriodicityList                 OPTIONAL,
    spatialRelationInformation      SpatialRelationInfo     OPTIONAL,
    pathlossReferenceInformation    PathlossReferenceInformation    OPTIONAL,
    iE-Extensions           ProtocolExtensionContainer { { SRSResourceSet-Item-ExtIEs} } OPTIONAL,
    ...
}

SRSResourceSet-Item-ExtIEs NRPPA-PROTOCOL-EXTENSION ::= {
    { ID id-SRSSpatialRelationPerSRSResource    CRITICALITY ignore   EXTENSION SpatialRelationPerSRSResource PRESENCE optional},
    ...
}

RequestType ::= ENUMERATED {activate, deactivate, ...}

ResourceSetType ::= CHOICE {
    periodic           ResourceSetTypePeriodic,
    semi-persistent    ResourceSetTypeSemi-persistent,
    aperiodic          ResourceSetTypeAperiodic,
    choice-extension               ProtocolIE-Single-Container {{ ResourceSetType-ExtIEs }}
}

ResourceSetType-ExtIEs NRPPA-PROTOCOL-IES ::= {
    ...
}

ResourceSetTypePeriodic ::= SEQUENCE {
periodicSet         ENUMERATED{true, ...},
    iE-Extensions       ProtocolExtensionContainer { { ResourceSetTypePeriodic-ExtIEs} }    OPTIONAL,
    ...
}

ResourceSetTypePeriodic-ExtIEs NRPPA-PROTOCOL-EXTENSION ::= {
    ...
}

ResourceSetTypeSemi-persistent ::= SEQUENCE {
semi-persistentSet ENUMERATED{true, ...},
    iE-Extensions       ProtocolExtensionContainer { { ResourceSetTypeSemi-persistent-ExtIEs} } OPTIONAL,
    ...
}

ResourceSetTypeSemi-persistent-ExtIEs NRPPA-PROTOCOL-EXTENSION ::= {
    ...




}

ResourceSetTypeAperiodic ::= SEQUENCE {
    sRSResourceTrigger          INTEGER(1..3),
    slotoffset                  INTEGER(0..32),
    iE-Extensions               ProtocolExtensionContainer { { ResourceSetTypeAperiodic-ExtIEs} } OPTIONAL,
    ...
}

ResourceSetTypeAperiodic-ExtIEs NRPPA-PROTOCOL-EXTENSION ::= {
    ...
}


ResourceType ::= CHOICE {
    periodic                          ResourceTypePeriodic,
    semi-persistent                   ResourceTypeSemi-persistent,
    aperiodic                         ResourceTypeAperiodic,
    choice-extension                  ProtocolIE-Single-Container {{ ResourceType-ExtIEs }}
}

ResourceType-ExtIEs NRPPA-PROTOCOL-IES ::= {
    ...
}

ResourceTypePeriodic ::= SEQUENCE {
    periodicity               ENUMERATED{slot1, slot2, slot4, slot5, slot8, slot10, slot16, slot20, slot32, slot40, slot64, slot80, slot160,
slot320, slot640, slot1280, slot2560, ...},
    offset                  INTEGER(0..2559, ...),
    iE-Extensions           ProtocolExtensionContainer { { ResourceTypePeriodic-ExtIEs} }   OPTIONAL,
    ...
}

ResourceTypePeriodic-ExtIEs NRPPA-PROTOCOL-EXTENSION ::= {
    ...
}

ResourceTypeSemi-persistent ::= SEQUENCE {
    periodicity         ENUMERATED{slot1, slot2, slot4, slot5, slot8, slot10, slot16, slot20, slot32, slot40, slot64, slot80, slot160, slot320,
slot640, slot1280, slot2560, ...},
    offset              INTEGER(0..2559, ...),
    iE-Extensions       ProtocolExtensionContainer { { ResourceTypeSemi-persistent-ExtIEs} }    OPTIONAL,
    ...
}

ResourceTypeSemi-persistent-ExtIEs NRPPA-PROTOCOL-EXTENSION ::= {
    ...
}

ResourceTypeAperiodic ::= SEQUENCE {
aperiodicResourceType      ENUMERATED{true, ...},
    iE-Extensions       ProtocolExtensionContainer { { ResourceTypeAperiodic-ExtIEs} }   OPTIONAL,
    ...
}





ResourceTypeAperiodic-ExtIEs NRPPA-PROTOCOL-EXTENSION ::= {
    ...
}


ResourceTypePos ::= CHOICE {
    periodic            ResourceTypePeriodicPos,
    semi-persistent     ResourceTypeSemi-persistentPos,
    aperiodic           ResourceTypeAperiodicPos,
    choice-extension                ProtocolIE-Single-Container {{ ResourceTypePos-ExtIEs }}
}

ResourceTypePos-ExtIEs NRPPA-PROTOCOL-IES ::= {
    ...
}

ResourceTypePeriodicPos ::= SEQUENCE {
periodicity        ENUMERATED{slot1, slot2, slot4, slot5, slot8, slot10, slot16, slot20, slot32, slot40, slot64, slot80, slot160, slot320, slot640,
slot1280, slot2560, slot5120, slot10240, slot40960, slot81920, ...},
offset              INTEGER(0..81919, ...),
    iE-Extensions       ProtocolExtensionContainer { { ResourceTypePeriodicPos-ExtIEs} }    OPTIONAL,
    ...
}

ResourceTypePeriodicPos-ExtIEs NRPPA-PROTOCOL-EXTENSION ::= {
    ...
}

ResourceTypeSemi-persistentPos ::= SEQUENCE {
periodicity        ENUMERATED{slot1, slot2, slot4, slot5, slot8, slot10, slot16, slot20, slot32, slot40, slot64, slot80, slot160, slot320, slot640,
slot1280, slot2560, slot5120, slot10240, slot40960, slot81920, ...},
offset              INTEGER(0..81919, ...),
    iE-Extensions       ProtocolExtensionContainer { { ResourceTypeSemi-persistentPos-ExtIEs} } OPTIONAL,
    ...
}

ResourceTypeSemi-persistentPos-ExtIEs NRPPA-PROTOCOL-EXTENSION ::= {
    ...
}

ResourceTypeAperiodicPos ::= SEQUENCE {
slotOffset          INTEGER (0..32),
    iE-Extensions       ProtocolExtensionContainer { { ResourceTypeAperiodicPos-ExtIEs} }   OPTIONAL,
    ...
}

ResourceTypeAperiodicPos-ExtIEs NRPPA-PROTOCOL-EXTENSION ::= {
    ...
}

ResponseTime ::= SEQUENCE {
    time          INTEGER (1..128,...),
    timeUnit      ENUMERATED {second, ten-seconds, ten-milliseconds,...},




    iE-Extensions        ProtocolExtensionContainer { { ResponseTime-ExtIEs} }    OPTIONAL,
    ...
}

ResponseTime-ExtIEs NRPPA-PROTOCOL-EXTENSION ::= {
    ...
}


ResultCSI-RSRP ::= SEQUENCE (SIZE (1.. maxCellReportNR)) OF ResultCSI-RSRP-Item

ResultCSI-RSRP-Item ::= SEQUENCE {
    nR-PCI                  NR-PCI,
    nR-ARFCN                NR-ARFCN,
    cGI-NR              CGI-NR                                                  OPTIONAL,
    valueCSI-RSRP-Cell      ValueRSRP-NR                                                OPTIONAL,
    cSI-RSRP-PerCSI-RS      ResultCSI-RSRP-PerCSI-RS                                    OPTIONAL,
    iE-Extensions       ProtocolExtensionContainer { { ResultCSI-RSRP-Item-ExtIEs} }    OPTIONAL,
    ...
}

ResultCSI-RSRP-Item-ExtIEs NRPPA-PROTOCOL-EXTENSION ::= {
    ...
}

ResultCSI-RSRP-PerCSI-RS ::= SEQUENCE (SIZE (1.. maxIndexesReport)) OF ResultCSI-RSRP-PerCSI-RS-Item

ResultCSI-RSRP-PerCSI-RS-Item ::= SEQUENCE {
    cSI-RS-Index        INTEGER (0..95),
    valueCSI-RSRP       ValueRSRP-NR,
    iE-Extensions       ProtocolExtensionContainer { { ResultCSI-RSRP-PerCSI-RS-Item-ExtIEs} }   OPTIONAL,
    ...
}

ResultCSI-RSRP-PerCSI-RS-Item-ExtIEs NRPPA-PROTOCOL-EXTENSION ::= {
    ...
}

ResultCSI-RSRQ ::= SEQUENCE (SIZE (1.. maxCellReportNR)) OF ResultCSI-RSRQ-Item

ResultCSI-RSRQ-Item ::= SEQUENCE {
    nR-PCI              NR-PCI,
    nR-ARFCN            NR-ARFCN,
    cGI-NR          CGI-NR                                                      OPTIONAL,
    valueCSI-RSRQ-Cell ValueRSRQ-NR                                                     OPTIONAL,
    cSI-RSRQ-PerCSI-RS      ResultCSI-RSRQ-PerCSI-RS                                    OPTIONAL,
    iE-Extensions       ProtocolExtensionContainer { { ResultCSI-RSRQ-Item-ExtIEs} }    OPTIONAL,
    ...
}

ResultCSI-RSRQ-Item-ExtIEs NRPPA-PROTOCOL-EXTENSION ::= {
    ...
}





ResultCSI-RSRQ-PerCSI-RS ::= SEQUENCE (SIZE (1.. maxIndexesReport)) OF ResultCSI-RSRQ-PerCSI-RS-Item

ResultCSI-RSRQ-PerCSI-RS-Item ::= SEQUENCE {
    cSI-RS-Index        INTEGER (0..95),
    valueCSI-RSRQ       ValueRSRQ-NR,
    iE-Extensions       ProtocolExtensionContainer { { ResultCSI-RSRQ-PerCSI-RS-Item-ExtIEs} }   OPTIONAL,
    ...
}

ResultCSI-RSRQ-PerCSI-RS-Item-ExtIEs NRPPA-PROTOCOL-EXTENSION ::= {
    ...
}

ResultEUTRA ::= SEQUENCE (SIZE (1.. maxEUTRAMeas)) OF ResultEUTRA-Item

ResultEUTRA-Item ::= SEQUENCE {
    pCI-EUTRA           PCI-EUTRA,
    eARFCN              EARFCN,
    valueRSRP-EUTRA     ValueRSRP-EUTRA                                             OPTIONAL,
    valueRSRQ-EUTRA     ValueRSRQ-EUTRA                                             OPTIONAL,
    cGI-EUTRA           CGI-EUTRA                                                   OPTIONAL,
    iE-Extensions       ProtocolExtensionContainer { { ResultEUTRA-Item-ExtIEs} }   OPTIONAL,
    ...
}

ResultEUTRA-Item-ExtIEs NRPPA-PROTOCOL-EXTENSION ::= {
    ...
}


ResultRSRP-EUTRA ::= SEQUENCE (SIZE (1.. maxCellReport)) OF ResultRSRP-EUTRA-Item

ResultRSRP-EUTRA-Item ::= SEQUENCE {
    pCI-EUTRA           PCI-EUTRA,
    eARFCN              EARFCN,
    cGI-EUTRA           CGI-EUTRA OPTIONAL,
    valueRSRP-EUTRA     ValueRSRP-EUTRA,
    iE-Extensions       ProtocolExtensionContainer { { ResultRSRP-EUTRA-Item-ExtIEs} } OPTIONAL,
    ...
}

ResultRSRP-EUTRA-Item-ExtIEs NRPPA-PROTOCOL-EXTENSION ::= {
    ...
}

ResultRSRQ-EUTRA ::= SEQUENCE (SIZE (1.. maxCellReport)) OF ResultRSRQ-EUTRA-Item

ResultRSRQ-EUTRA-Item ::= SEQUENCE {
    pCI-EUTRA           PCI-EUTRA,
    eARFCN              EARFCN,
    cGI-UTRA            CGI-EUTRA OPTIONAL,
    valueRSRQ-EUTRA     ValueRSRQ-EUTRA,
    iE-Extensions       ProtocolExtensionContainer { { ResultRSRQ-EUTRA-Item-ExtIEs} } OPTIONAL,
    ...




}

ResultRSRQ-EUTRA-Item-ExtIEs NRPPA-PROTOCOL-EXTENSION ::= {
    ...
}


ResultSS-RSRP ::= SEQUENCE (SIZE (1.. maxCellReportNR)) OF ResultSS-RSRP-Item

ResultSS-RSRP-Item ::= SEQUENCE {
    nR-PCI              NR-PCI,
    nR-ARFCN            NR-ARFCN,
    cGI-NR          CGI-NR                                                  OPTIONAL,
    valueSS-RSRP-Cell   ValueRSRP-NR                                                OPTIONAL,
    sS-RSRP-PerSSB      ResultSS-RSRP-PerSSB                                        OPTIONAL,
    iE-Extensions       ProtocolExtensionContainer { { ResultSS-RSRP-Item-ExtIEs} } OPTIONAL,
    ...
}

ResultSS-RSRP-Item-ExtIEs NRPPA-PROTOCOL-EXTENSION ::= {
    ...
}

ResultSS-RSRP-PerSSB ::= SEQUENCE (SIZE (1.. maxIndexesReport)) OF ResultSS-RSRP-PerSSB-Item

ResultSS-RSRP-PerSSB-Item ::= SEQUENCE {
    sSB-Index           SSB-Index,
    valueSS-RSRP        ValueRSRP-NR,
    iE-Extensions       ProtocolExtensionContainer { { ResultSS-RSRP-PerSSB-Item-ExtIEs} }   OPTIONAL,
    ...
}

ResultSS-RSRP-PerSSB-Item-ExtIEs NRPPA-PROTOCOL-EXTENSION ::= {
    ...
}

ResultSS-RSRQ ::= SEQUENCE (SIZE (1.. maxCellReportNR)) OF ResultSS-RSRQ-Item

ResultSS-RSRQ-Item ::= SEQUENCE {
    nR-PCI              NR-PCI,
    nR-ARFCN            NR-ARFCN,
    cGI-NR          CGI-NR                                                  OPTIONAL,
    valueSS-RSRQ-Cell   ValueRSRQ-NR                                                OPTIONAL,
    sS-RSRQ-PerSSB      ResultSS-RSRQ-PerSSB                                        OPTIONAL,
    iE-Extensions       ProtocolExtensionContainer { { ResultSS-RSRQ-Item-ExtIEs} } OPTIONAL,
    ...
}

ResultSS-RSRQ-Item-ExtIEs NRPPA-PROTOCOL-EXTENSION ::= {
    ...
}

ResultSS-RSRQ-PerSSB ::= SEQUENCE (SIZE (1.. maxIndexesReport)) OF ResultSS-RSRQ-PerSSB-Item





ResultSS-RSRQ-PerSSB-Item ::= SEQUENCE {
    sSB-Index           SSB-Index,
    valueSS-RSRQ        ValueRSRQ-NR,
    iE-Extensions       ProtocolExtensionContainer { { ResultSS-RSRQ-PerSSB-Item-ExtIEs} }    OPTIONAL,
    ...
}

ResultSS-RSRQ-PerSSB-Item-ExtIEs NRPPA-PROTOCOL-EXTENSION ::= {
    ...
}


ResultGERAN ::= SEQUENCE (SIZE (1.. maxGERANMeas)) OF ResultGERAN-Item

ResultGERAN-Item ::= SEQUENCE {
    bCCH                BCCH,
    physCellIDGERAN     PhysCellIDGERAN,
    rSSI                RSSI,
    iE-Extensions       ProtocolExtensionContainer { { ResultGERAN-Item-ExtIEs} } OPTIONAL,
    ...
}

ResultGERAN-Item-ExtIEs NRPPA-PROTOCOL-EXTENSION ::= {
    ...
}


ResultNR ::= SEQUENCE (SIZE (1.. maxNRMeas)) OF ResultNR-Item

ResultNR-Item ::= SEQUENCE {
    nR-PCI              NR-PCI,
    nR-ARFCN            NR-ARFCN,
    valueSS-RSRP-Cell   ValueRSRP-NR                                             OPTIONAL,
    valueSS-RSRQ-Cell   ValueRSRQ-NR                                             OPTIONAL,
    sS-RSRP-PerSSB      ResultSS-RSRP-PerSSB                                     OPTIONAL,
    sS-RSRQ-PerSSB      ResultSS-RSRQ-PerSSB                                     OPTIONAL,
    cGI-NR              CGI-NR                                                   OPTIONAL,
    iE-Extensions       ProtocolExtensionContainer { { ResultNR-Item-ExtIEs} }   OPTIONAL,
    ...
}

ResultNR-Item-ExtIEs NRPPA-PROTOCOL-EXTENSION ::= {
    ...
}


ResultUTRAN ::= SEQUENCE (SIZE (1.. maxUTRANMeas)) OF ResultUTRAN-Item

ResultUTRAN-Item ::= SEQUENCE {
    uARFCN              UARFCN,
    physCellIDUTRAN     CHOICE {
        physCellIDUTRA-FDD      PhysCellIDUTRA-FDD,
        physCellIDUTRA-TDD      PhysCellIDUTRA-TDD
    },




    uTRA-RSCP            UTRA-RSCP OPTIONAL,
    uTRA-EcN0            UTRA-EcN0 OPTIONAL,
    iE-Extensions        ProtocolExtensionContainer { { ResultUTRAN-Item-ExtIEs} } OPTIONAL,
    ...
}

ResultUTRAN-Item-ExtIEs NRPPA-PROTOCOL-EXTENSION ::= {
    ...
}

RSSI ::= INTEGER (0..63, ...)

-- S

SCS-SpecificCarrier ::= SEQUENCE {
    offsetToCarrier                     INTEGER (0..2199,...),
    subcarrierSpacing                   ENUMERATED {kHz15, kHz30, kHz60, kHz120,...},
    carrierBandwidth                    INTEGER (1..275,...),
iE-Extensions                   ProtocolExtensionContainer { { SCS-SpecificCarrier-ExtIEs } } OPTIONAL,
    ...
}

SCS-SpecificCarrier-ExtIEs NRPPA-PROTOCOL-EXTENSION ::= {
    ...
}


Search-window-information ::= SEQUENCE {
    expectedPropagationDelay        INTEGER (-3841..3841,...),
    delayUncertainty                INTEGER (1..246,...),
    iE-Extensions                   ProtocolExtensionContainer { { Search-window-information-ExtIEs } } OPTIONAL,
    ...
}

Search-window-information-ExtIEs NRPPA-PROTOCOL-EXTENSION ::= {
    ...
}


RelativeTime1900 ::= BIT STRING (SIZE (64))


SFNInitialisationTime-EUTRA ::= BIT STRING (SIZE (64))

SlotNumber ::= INTEGER (0..79)

SpatialDirectionInformation ::= SEQUENCE {
    nR-PRS-Beam-Information         NR-PRS-Beam-Information,
    iE-Extensions                   ProtocolExtensionContainer { { SpatialDirectionInformation-ExtIEs } } OPTIONAL,
    ...
}

SpatialDirectionInformation-ExtIEs NRPPA-PROTOCOL-EXTENSION ::= {
    ...




}


SpatialRelationInfo ::= SEQUENCE {
    spatialRelationforResourceID                    SpatialRelationforResourceID,
    iE-Extensions       ProtocolExtensionContainer { {SpatialRelationInfo-ExtIEs} } OPTIONAL,
    ...
}

SpatialRelationInfo-ExtIEs NRPPA-PROTOCOL-EXTENSION ::= {
    ...
}


SpatialRelationforResourceID ::= SEQUENCE (SIZE(1..maxnoSpatialRelations)) OF SpatialRelationforResourceIDItem

SpatialRelationforResourceIDItem ::= SEQUENCE {
    referenceSignal     ReferenceSignal,
    iE-Extensions       ProtocolExtensionContainer { {SpatialRelationforResourceIDItem-ExtIEs} } OPTIONAL,
    ...
}

SpatialRelationforResourceIDItem-ExtIEs NRPPA-PROTOCOL-EXTENSION ::= {
    ...
}


SpatialRelationPerSRSResource ::= SEQUENCE {
    spatialRelationPerSRSResource-List SpatialRelationPerSRSResource-List,
    iE-Extensions       ProtocolExtensionContainer { { SpatialRelationPerSRSResource-ExtIEs} }   OPTIONAL,
    ...
}

SpatialRelationPerSRSResource-ExtIEs NRPPA-PROTOCOL-EXTENSION ::= {
    ...
}

SpatialRelationPerSRSResource-List::= SEQUENCE(SIZE (1.. maxnoSRS-ResourcePerSet)) OF SpatialRelationPerSRSResourceItem

SpatialRelationPerSRSResourceItem ::= SEQUENCE {
    referenceSignal     ReferenceSignal,
    iE-Extensions       ProtocolExtensionContainer { {SpatialRelationPerSRSResourceItem-ExtIEs} } OPTIONAL,
    ...
}

SpatialRelationPerSRSResourceItem-ExtIEs NRPPA-PROTOCOL-EXTENSION ::= {
    ...
}

SpatialRelationPos ::= CHOICE {
    sSBPos                  SSB,
    pRSInformationPos       PRSInformationPos,
    choice-extension                ProtocolIE-Single-Container {{ SpatialInformationPos-ExtIEs }}
}





SpatialInformationPos-ExtIEs NRPPA-PROTOCOL-IES ::= {
    ...
}



SRSConfig ::= SEQUENCE {
    sRSResource-List              SRSResource-List OPTIONAL,
    posSRSResource-List           PosSRSResource-List OPTIONAL,
    sRSResourceSet-List           SRSResourceSet-List OPTIONAL,
    posSRSResourceSet-List        PosSRSResourceSet-List OPTIONAL,
    iE-Extensions                     ProtocolExtensionContainer { { SRSConfig-ExtIEs } } OPTIONAL,
    ...
}

SRSConfig-ExtIEs NRPPA-PROTOCOL-EXTENSION ::= {
    ...
}

SRSCarrier-List ::= SEQUENCE (SIZE(1.. maxnoSRS-Carriers)) OF SRSCarrier-List-Item

SRSCarrier-List-Item ::= SEQUENCE {
    pointA                          INTEGER (0..3279165),
    uplinkChannelBW-PerSCS-List     UplinkChannelBW-PerSCS-List,
    activeULBWP                     ActiveULBWP,
    pCI-NR                          INTEGER (0..1007)       OPTIONAL,
iE-Extensions                   ProtocolExtensionContainer { { SRSCarrier-List-Item-ExtIEs } } OPTIONAL,
    ...
}

SRSCarrier-List-Item-ExtIEs NRPPA-PROTOCOL-EXTENSION ::= {
    ...
}


SRSConfiguration ::= SEQUENCE {
    sRSCarrier-List     SRSCarrier-List,
    iE-Extensions           ProtocolExtensionContainer { { SRSConfiguration-ExtIEs } } OPTIONAL,
    ...
}

SRSConfiguration-ExtIEs NRPPA-PROTOCOL-EXTENSION ::= {
    ...
}

SrsFrequency ::= INTEGER (0..3279165)

SRSPortIndex ::= ENUMERATED{id1000, id1001, id1002, id1003, ...}

SRSPosResourceID ::= INTEGER (0..63)

SRSResource::= SEQUENCE {
    sRSResourceID                     SRSResourceID,




    nrofSRS-Ports                     ENUMERATED {port1, ports2, ports4},
    transmissionComb                  TransmissionComb,
    startPosition                     INTEGER (0..13),
    nrofSymbols                       ENUMERATED {n1, n2, n4},
    repetitionFactor                  ENUMERATED {n1, n2, n4},
    freqDomainPosition                INTEGER (0..67),
    freqDomainShift                   INTEGER (0..268),
    c-SRS                             INTEGER (0..63),
    b-SRS                             INTEGER (0..3),
    b-hop                             INTEGER (0..3),
    groupOrSequenceHopping            ENUMERATED { neither, groupHopping, sequenceHopping },
    resourceType                      ResourceType,
    sequenceId                        INTEGER (0..1023),
    iE-Extensions                     ProtocolExtensionContainer { { SRSResource-ExtIEs } } OPTIONAL,
    ...
}

SRSResource-ExtIEs NRPPA-PROTOCOL-EXTENSION ::= {
    ...
}

SRSResourceID ::= INTEGER (0..63)

SRSResource-List ::= SEQUENCE (SIZE (1..maxnoSRS-Resources)) OF SRSResource

SRSResourceSet-List ::= SEQUENCE (SIZE (1..maxnoSRS-ResourceSets)) OF SRSResourceSet

SRSResourceID-List::= SEQUENCE (SIZE (1..maxnoSRS-ResourcePerSet)) OF SRSResourceID

SRSResourceSet::= SEQUENCE {
    sRSResourceSetID                  INTEGER(0..15),
    sRSResourceID-List                SRSResourceID-List,
    resourceSetType                   ResourceSetType,
    iE-Extensions                     ProtocolExtensionContainer { { SRSResourceSet-ExtIEs } } OPTIONAL,
    ...
}

SRSResourceSet-ExtIEs NRPPA-PROTOCOL-EXTENSION ::= {
    ...
}

SRSResourceSetID ::= INTEGER (0..15, ...)

SRSResourceTrigger ::= SEQUENCE {
    aperiodicSRSResourceTriggerList                 AperiodicSRSResourceTriggerList,
    iE-Extensions       ProtocolExtensionContainer { {SRSResourceTrigger-ExtIEs} } OPTIONAL,
    ...
}

SRSResourceTrigger-ExtIEs NRPPA-PROTOCOL-EXTENSION ::= {
    ...
}

SRSResourcetype ::= SEQUENCE {




    sRSResourceTypeChoice                   SRSResourceTypeChoice,
    iE-Extensions       ProtocolExtensionContainer { { SRSResourcetype-ExtIEs} }     OPTIONAL,
    ...
}

SRSResourcetype-ExtIEs NRPPA-PROTOCOL-EXTENSION ::= {
    { ID id-SRSPortIndex    CRITICALITY ignore EXTENSION SRSPortIndex   PRESENCE optional},
    ...
}

SRSResourceTypeChoice ::= CHOICE {
    sRSResourceInfo         SRSInfo,
    posSRSResourceInfo      PosSRSInfo,
    ...
}

SRSInfo ::= SEQUENCE {
    sRSResource          SRSResourceID,
    ...
}

PosSRSInfo ::= SEQUENCE {
    posSRSResourceID         SRSPosResourceID,
    ...
}


SSBInfo ::= SEQUENCE {
    listOfSSBInfo        SEQUENCE (SIZE (1..maxNoSSBs)) OF SSBInfoItem,
    iE-Extensions        ProtocolExtensionContainer { {SSBInfo-ExtIEs} } OPTIONAL,
    ...
}

SSBInfo-ExtIEs NRPPA-PROTOCOL-EXTENSION ::= {
    ...
}



SSBInfoItem ::= SEQUENCE {
    sSB-Configuration   TF-Configuration,
    pCI-NR              INTEGER (0..1007),
    iE-Extensions       ProtocolExtensionContainer { { SSBInfoItem-ExtIEs} }    OPTIONAL,
    ...
}


SSBInfoItem-ExtIEs NRPPA-PROTOCOL-EXTENSION ::= {
    ...
}


SSB ::= SEQUENCE {
    pCI-NR               INTEGER   (0..1007),




    ssb-index            SSB-Index   OPTIONAL,
    iE-Extensions        ProtocolExtensionContainer { {SSB-ExtIEs} } OPTIONAL,
    ...
}

SSB-ExtIEs NRPPA-PROTOCOL-EXTENSION ::= {
    ...
}


SSBBurstPosition ::= CHOICE {
    shortBitmap         BIT STRING (SIZE(4)),
    mediumBitmap        BIT STRING (SIZE(8)),
    longBitmap          BIT STRING (SIZE(64)),
    choice-extension        ProtocolIE-Single-Container { { SSBBurstPosition-ExtIEs} }
}

SSBBurstPosition-ExtIEs NRPPA-PROTOCOL-IES ::= {
    ...
}

SSB-Index ::= INTEGER(0..63)


SSID ::= OCTET STRING (SIZE(1..32))

StartTimeAndDuration ::= SEQUENCE {
    startTime           RelativeTime1900                OPTIONAL,
    duration            INTEGER (0..90060, ...)         OPTIONAL,
    iE-Extensions       ProtocolExtensionContainer { { StartTimeAndDuration-ExtIEs} }    OPTIONAL,
    ...
}

StartTimeAndDuration-ExtIEs NRPPA-PROTOCOL-EXTENSION ::= {
    ...
}

SystemFrameNumber ::= INTEGER (0..1023)

SystemInformation ::= SEQUENCE (SIZE (1.. maxNrOfPosSImessage)) OF SEQUENCE {
    broadcastPeriodicity                BroadcastPeriodicity,
    posSIBs                             PosSIBs,
    iE-Extensions                       ProtocolExtensionContainer { { SystemInformation-ExtIEs} }   OPTIONAL,
    ...
}

SystemInformation-ExtIEs NRPPA-PROTOCOL-EXTENSION ::= {
    ...
}


-- T

TAC ::= OCTET STRING (SIZE(3))





TDD-Config-EUTRA-Item ::= SEQUENCE {
    subframeAssignment          ENUMERATED { sa0, sa1, sa2, sa3, sa4, sa5, sa6, ... },
    iE-Extensions               ProtocolExtensionContainer { { TDD-Config-EUTRA-Item-Item-ExtIEs } } OPTIONAL,
    ...
}

TDD-Config-EUTRA-Item-Item-ExtIEs NRPPA-PROTOCOL-EXTENSION ::= {
    ...
}

TRPTEGIDInformation ::= CHOICE {
    rxTx-TEG            RxTxTEG,
    rx-TEG              RxTEG,
    choice-extension        ProtocolIE-Single-Container { { TRPTEGIDInformation-ExtIEs} }
}

TRPTEGIDInformation-ExtIEs NRPPA-PROTOCOL-IES ::= {
    ...
}

RxTxTEG ::= SEQUENCE {
    tRP-RxTx-TEGID       INTEGER (0..255),
    tRP-Tx-TEGID         INTEGER (0..7) OPTIONAL,
    iE-extensions        ProtocolExtensionContainer { { RxTxTEG-ExtIEs } }        OPTIONAL,
    ...
}

RxTxTEG-ExtIEs NRPPA-PROTOCOL-EXTENSION ::= {
    { ID id-TRPRxTxTimingErrorMargin        CRITICALITY ignore EXTENSION TimingErrorMargin    PRESENCE optional }|
    { ID id-TRPTxTimingErrorMargin          CRITICALITY ignore EXTENSION TimingErrorMargin    PRESENCE optional },
    ...
}

RxTEG ::= SEQUENCE {
    tRP-Rx-TEGID          INTEGER (0..31),
    tRP-Tx-TEGID          INTEGER (0..7),
    iE-extensions        ProtocolExtensionContainer { { RxTEG-ExtIEs } }   OPTIONAL,
    ...
}

RxTEG-ExtIEs NRPPA-PROTOCOL-EXTENSION ::= {
    { ID id-TRPRxTimingErrorMargin          CRITICALITY ignore EXTENSION TimingErrorMargin    PRESENCE optional }|
    { ID id-TRPTxTimingErrorMargin          CRITICALITY ignore EXTENSION TimingErrorMargin    PRESENCE optional },
    ...
}

TimingErrorMargin            ::= ENUMERATED {tc0, tc2, tc4, tc6, tc8, tc12, tc16, tc20, tc24, tc32, tc40, tc48, tc56, tc64, tc72, tc80, ...}

TF-Configuration ::= SEQUENCE {
    sSB-frequency               INTEGER (0..3279165),
    sSB-subcarrier-spacing      ENUMERATED {kHz15, kHz30, kHz120, kHz240, ..., kHz60},
    sSB-Transmit-power          INTEGER (-60..50),
    sSB-periodicity             ENUMERATED {ms5, ms10, ms20, ms40, ms80, ms160, ...},




    sSB-half-frame-offset       INTEGER(0..1),
    sSB-SFN-offset              INTEGER(0..15),
    sSB-BurstPosition           SSBBurstPosition    OPTIONAL,
    sFN-initialisation-time     RelativeTime1900     OPTIONAL,
    iE-Extensions       ProtocolExtensionContainer { { TF-Configuration-ExtIEs} }    OPTIONAL,
    ...
}

TF-Configuration-ExtIEs NRPPA-PROTOCOL-EXTENSION ::= {
    ...
}


TimeStamp ::= SEQUENCE {
    systemFrameNumber        SystemFrameNumber,
    slotIndex                TimeStampSlotIndex,
    measurementTime          RelativeTime1900    OPTIONAL,
    iE-Extension             ProtocolExtensionContainer { { TimeStamp-ExtIEs} }   OPTIONAL,
    ...
}

TimeStamp-ExtIEs NRPPA-PROTOCOL-EXTENSION ::= {
    ...
}

TimeStampSlotIndex ::= CHOICE {
    sCS-15          INTEGER(0..9),
    sCS-30          INTEGER(0..19),
    sCS-60          INTEGER(0..39),
    sCS-120         INTEGER(0..79),
    choice-extension        ProtocolIE-Single-Container { { TimeStampSlotIndex-ExtIEs} }
}

TimeStampSlotIndex-ExtIEs NRPPA-PROTOCOL-IES ::= {
    ...
}


TP-ID-EUTRA ::= INTEGER (0..4095, ...)

TP-Type-EUTRA ::= ENUMERATED { prs-only-tp, ... }


TransmissionComb ::= CHOICE {
    n2    SEQUENCE {
            combOffset-n2                  INTEGER (0..1),
            cyclicShift-n2                 INTEGER (0..7)
        },
    n4    SEQUENCE {
            combOffset-n4                  INTEGER (0..3),
            cyclicShift-n4                 INTEGER (0..11)
        },
    choice-extension                  ProtocolIE-Single-Container { { TransmissionComb-ExtIEs} }
}




TransmissionComb-ExtIEs NRPPA-PROTOCOL-IES ::= {
    ...
}

TransmissionCombPos ::= CHOICE {
    n2    SEQUENCE {
            combOffset-n2                  INTEGER (0..1),
            cyclicShift-n2                 INTEGER (0..7)
        },
    n4    SEQUENCE {
            combOffset-n4                  INTEGER (0..3),
            cyclicShift-n4                 INTEGER (0..11)
        },
    n8    SEQUENCE {
            combOffset-n8                  INTEGER (0..7),
            cyclicShift-n8                 INTEGER (0..5)
        },

    choice-extension                ProtocolIE-Single-Container { { TransmissionCombPos-ExtIEs} }
}
TransmissionCombPos-ExtIEs NRPPA-PROTOCOL-IES ::= {
    ...
}

TRPBeamAntennaInformation ::= SEQUENCE {
    choice-TRP-Beam-Antenna-Info-Item       Choice-TRP-Beam-Antenna-Info-Item,
    iE-Extensions           ProtocolExtensionContainer {{ TRPBeamAntennaInformation-ExtIEs}}           OPTIONAL,
    ...
}

TRPBeamAntennaInformation-ExtIEs NRPPA-PROTOCOL-EXTENSION ::= {
    ...
}

Choice-TRP-Beam-Antenna-Info-Item ::= CHOICE {
    reference                   TRP-ID,
    explicit                    TRP-BeamAntennaExplicitInformation,
    noChange                    NULL,
    choice-extension                ProtocolIE-Single-Container { { Choice-TRP-Beam-Info-Item-ExtIEs } }
}

Choice-TRP-Beam-Info-Item-ExtIEs NRPPA-PROTOCOL-IES ::= {
    ...
}

TRP-BeamAntennaExplicitInformation ::= SEQUENCE {
    trp-BeamAntennaAngles                   TRP-BeamAntennaAngles,
    lcs-to-gcs-translation                  LCS-to-GCS-Translation                                   OPTIONAL,
    iE-Extensions           ProtocolExtensionContainer {{ TRP-BeamAntennaExplicitInformation-ExtIEs}}            OPTIONAL,
    ...
}

TRP-BeamAntennaExplicitInformation-ExtIEs NRPPA-PROTOCOL-EXTENSION ::= {
    ...




}

TRP-BeamAntennaAngles ::= SEQUENCE (SIZE (1.. maxnoAzimuthAngles)) OF TRP-BeamAntennaAnglesList-Item

TRP-BeamAntennaAnglesList-Item ::= SEQUENCE {
    trp-azimuth-angle                   INTEGER (0..359),
    trp-azimuth-angle-fine              INTEGER (0..9) OPTIONAL,
    trp-elevation-angle-list            SEQUENCE (SIZE (1.. maxnoElevationAngles)) OF TRP-ElevationAngleList-Item,
    iE-Extensions           ProtocolExtensionContainer {{ TRP-BeamAntennaAnglesList-Item-ExtIEs}}       OPTIONAL,
    ...
}

TRP-BeamAntennaAnglesList-Item-ExtIEs NRPPA-PROTOCOL-EXTENSION ::= {
    ...
}

TRP-ElevationAngleList-Item ::= SEQUENCE {
    trp-elevation-angle                 INTEGER (0..180),
    trp-elevation-angle-fine            INTEGER (0..9) OPTIONAL,
    trp-beam-power-list                 SEQUENCE (SIZE (2..maxNumResourcesPerAngle)) OF TRP-Beam-Power-Item,
    iE-Extensions           ProtocolExtensionContainer {{ TRP-ElevationAngleList-Item-ExtIEs}}       OPTIONAL,
    ...
}

TRP-ElevationAngleList-Item-ExtIEs NRPPA-PROTOCOL-EXTENSION ::= {
    ...
}

TRP-Beam-Power-Item ::= SEQUENCE {
    pRSResourceSetID                PRS-Resource-Set-ID     OPTIONAL,
    pRSResourceID                   PRS-Resource-ID,
    relativePower               INTEGER (0..30), --negative value
    relativePowerFine               INTEGER (0..9)          OPTIONAL, --negative value
    iE-Extensions           ProtocolExtensionContainer {{ TRP-Beam-Power-Item-ExtIEs}}                 OPTIONAL,
    ...
}

TRP-Beam-Power-Item-ExtIEs NRPPA-PROTOCOL-EXTENSION ::= {
    ...
}

TRPMeasurementQuantities ::= SEQUENCE (SIZE (1..maxnoPosMeas)) OF TRPMeasurementQuantitiesList-Item

TRPMeasurementQuantitiesList-Item ::= SEQUENCE {
    tRPMeasurementQuantities-Item       TRPMeasurementQuantities-Item,
    timingReportingGranularityFactor    INTEGER (0..5) OPTIONAL,
    iE-Extensions           ProtocolExtensionContainer {{ TRPMeasurementQuantitiesList-Item-ExtIEs}}     OPTIONAL,
    ...
}

TRPMeasurementQuantitiesList-Item-ExtIEs NRPPA-PROTOCOL-EXTENSION ::= {
    ...
}





TRPMeasurementQuantities-Item ::= ENUMERATED {
    gNB-RxTxTimeDiff,
    uL-SRS-RSRP,
    uL-AoA,
    uL-RTOA,
    ...,
    multiple-UL-AoA,
    uL-SRS-RSRPP
}

TrpMeasurementResult ::= SEQUENCE (SIZE (1.. maxnoPosMeas)) OF TrpMeasurementResultItem
TrpMeasurementResultItem ::= SEQUENCE {
    measuredResultsValue                TrpMeasuredResultsValue,
    timeStamp                           TimeStamp,
    measurementQuality                  TrpMeasurementQuality                       OPTIONAL,
    measurementBeamInfo                 MeasurementBeamInfo             OPTIONAL,
    iE-Extensions       ProtocolExtensionContainer {{TrpMeasurementResultItem-ExtIEs}}      OPTIONAL,
    ...
}

TrpMeasurementResultItem-ExtIEs NRPPA-PROTOCOL-EXTENSION ::= {
    { ID id-SRSResourcetype CRITICALITY ignore EXTENSION SRSResourcetype PRESENCE optional}|
    { ID id-ARP-ID      CRITICALITY ignore EXTENSION ARP-ID     PRESENCE optional}|
    { ID id-LoS-NLoSInformation     CRITICALITY ignore EXTENSION LoS-NLoSInformation        PRESENCE optional },
    ...
}

TrpMeasuredResultsValue ::= CHOICE {
    uL-AngleOfArrival   UL-AoA,
    uL-SRS-RSRP         UL-SRS-RSRP,
    uL-RTOA             UL-RTOAMeasurement,
    gNB-RxTxTimeDiff    GNB-RxTxTimeDiff,
    choice-extension                             ProtocolIE-Single-Container { { TrpMeasuredResultsValue-ExtIEs } }
}

TrpMeasuredResultsValue-ExtIEs NRPPA-PROTOCOL-IES ::= {
    { ID id-ZoA     CRITICALITY reject TYPE ZoA PRESENCE mandatory}|
    { ID id-MultipleULAoA   CRITICALITY reject TYPE MultipleULAoA PRESENCE mandatory}|
    { ID id-UL-SRS-RSRPP    CRITICALITY reject TYPE UL-SRS-RSRPP PRESENCE mandatory},
    ...
}

TrpMeasurementQuality ::= CHOICE {
    timingMeasQuality       TrpMeasurementTimingQuality,
    angleMeasQuality        TrpMeasurementAngleQuality,
    choice-Extension        ProtocolIE-Single-Container {{ TrpMeasurementQuality-ExtIEs}}

}

TrpMeasurementQuality-ExtIEs NRPPA-PROTOCOL-IES ::= {
    ...
}

TrpMeasurementTimingQuality ::= SEQUENCE {




    measurementQuality       INTEGER (0..31),
    resolution               ENUMERATED {m0dot1, m1, m10, m30, ...},
    iE-extensions            ProtocolExtensionContainer { { TrpMeasurementTimingQuality-ExtIEs } } OPTIONAL,
    ...
}

TrpMeasurementTimingQuality-ExtIEs NRPPA-PROTOCOL-EXTENSION ::= {
    ...
}

TrpMeasurementAngleQuality ::= SEQUENCE {
    azimuthQuality      INTEGER (0..255),
    zenithQuality       INTEGER (0..255)    OPTIONAL,
    resolution          ENUMERATED {deg0dot1, ...},
    iE-extensions       ProtocolExtensionContainer { { TrpMeasurementAngleQuality-ExtIEs } } OPTIONAL,
    ...
}

TrpMeasurementAngleQuality-ExtIEs NRPPA-PROTOCOL-EXTENSION ::= {
    ...
}

TRP-MeasurementRequestList ::= SEQUENCE (SIZE (1..maxNoOfMeasTRPs)) OF TRP-MeasurementRequestItem

TRP-MeasurementRequestItem ::= SEQUENCE {
    tRP-ID                          TRP-ID,
    search-window-information       Search-window-information   OPTIONAL,
    iE-extensions                   ProtocolExtensionContainer { { TRP-MeasurementRequestItem-ExtIEs } } OPTIONAL,
    ...
}

TRP-MeasurementRequestItem-ExtIEs NRPPA-PROTOCOL-EXTENSION ::= {
    { ID id-Cell-ID     CRITICALITY ignore EXTENSION CGI-NR     PRESENCE optional }|
    { ID id-AoA-SearchWindow        CRITICALITY ignore EXTENSION AoA-AssistanceInfo     PRESENCE optional }|
    { ID id-NumberOfTRPRxTEG        CRITICALITY ignore EXTENSION NumberOfTRPRxTEG       PRESENCE optional }|
    { ID id-NumberOfTRPRxTxTEG      CRITICALITY ignore EXTENSION NumberOfTRPRxTxTEG     PRESENCE optional },
    ...
}

TRP-MeasurementResponseList ::= SEQUENCE (SIZE (1..maxNoOfMeasTRPs)) OF TRP-MeasurementResponseItem

TRP-MeasurementResponseItem ::= SEQUENCE {
    tRP-ID                          TRP-ID,
    measurementResult               TrpMeasurementResult,
    iE-extensions                   ProtocolExtensionContainer { { TRP-MeasurementResponseItem-ExtIEs } } OPTIONAL,
    ...
}

TRP-MeasurementResponseItem-ExtIEs NRPPA-PROTOCOL-EXTENSION ::= {
    { ID id-Cell-ID     CRITICALITY ignore EXTENSION CGI-NR     PRESENCE optional },
    ...
}





TRP-MeasurementUpdateList ::= SEQUENCE (SIZE (1..maxNoOfMeasTRPs)) OF TRP-MeasurementUpdateItem

TRP-MeasurementUpdateItem ::= SEQUENCE {
    tRP-ID                      TRP-ID,
    aoA-window-information      AoA-AssistanceInfo OPTIONAL,
    iE-extensions                   ProtocolExtensionContainer { { TRP-MeasurementUpdateItem-ExtIEs } } OPTIONAL,
    ...
}

TRP-MeasurementUpdateItem-ExtIEs NRPPA-PROTOCOL-EXTENSION ::= {
    { ID id-NumberOfTRPRxTEG        CRITICALITY ignore EXTENSION NumberOfTRPRxTEG        PRESENCE optional }|
    { ID id-NumberOfTRPRxTxTEG      CRITICALITY ignore EXTENSION NumberOfTRPRxTxTEG      PRESENCE optional },
    ...
}


TRPInformationListTRPResp ::= SEQUENCE (SIZE (1.. maxnoTRPs)) OF SEQUENCE {
    tRPInformation                  TRPInformation,
    iE-Extensions                   ProtocolExtensionContainer { {TRPInformationTRPResp-ExtIEs} } OPTIONAL,
    ...
}

TRPInformationTRPResp-ExtIEs NRPPA-PROTOCOL-EXTENSION ::= {
    ...
}

TRPInformation ::= SEQUENCE {
    tRP-ID                            TRP-ID,
    tRPInformationTypeResponseList    TRPInformationTypeResponseList,
    iE-Extensions                     ProtocolExtensionContainer { { TRPInformation-ExtIEs } }     OPTIONAL,
    ...
}

TRPInformation-ExtIEs NRPPA-PROTOCOL-EXTENSION ::= {
    ...
}

TRPInformationTypeResponseList ::= SEQUENCE (SIZE (1..maxnoTRPInfoTypes)) OF TRPInformationTypeResponseItem

TRPInformationTypeResponseItem ::= CHOICE {
    pCI-NR                                      INTEGER (0..1007),
    cGI-NR                                  CGI-NR,
    aRFCN                                       INTEGER (0..3279165),
    pRSConfiguration                            PRSConfiguration,
    sSBinformation                              SSBInfo,
    sFNInitialisationTime                       RelativeTime1900,
    spatialDirectionInformation                 SpatialDirectionInformation,
    geographicalCoordinates                     GeographicalCoordinates,
    choice-extension                            ProtocolIE-Single-Container { { TRPInformationTypeResponseItem-ExtIEs } }
}

TRPInformationTypeResponseItem-ExtIEs NRPPA-PROTOCOL-IES ::= {
    { ID id-TRPType                     CRITICALITY reject TYPE TRPType                   PRESENCE mandatory }|
    { ID id-OnDemandPRS             CRITICALITY reject TYPE OnDemandPRS-Info          PRESENCE mandatory}|




    { ID id-TRPTxTEGAssociation            CRITICALITY reject TYPE TRPTxTEGAssociation     PRESENCE mandatory}|
    { ID id-TRPBeamAntennaInformation      CRITICALITY reject TYPE TRPBeamAntennaInformation   PRESENCE mandatory },
    ...

}


TRPInformationTypeListTRPReq ::= SEQUENCE (SIZE(1.. maxnoTRPInfoTypes)) OF ProtocolIE-Single-Container { {TRPInformationTypeItemTRPReq} }

TRPInformationTypeItemTRPReq NRPPA-PROTOCOL-IES ::= {
    { ID id-TRPInformationTypeItem   CRITICALITY reject       TYPE TRPInformationTypeItem     PRESENCE mandatory },
    ...
}

TRPInformationTypeItem ::= ENUMERATED {
        nrPCI,
        nG-RAN-CGI,
        arfcn,
        pRSConfig,
        sSBInfo,
        sFNInitTime,
        spatialDirectInfo,
        geoCoord,

        ...,
        trp-type,
        ondemandPRSInfo,
        trpTxTeg,
        beam-antenna-info
}

TRPList ::= SEQUENCE (SIZE(1.. maxnoTRPs)) OF TRPItem

TRPItem ::= SEQUENCE {
        tRP-ID      TRP-ID,
    iE-Extensions   ProtocolExtensionContainer { {TRPItem-ExtIEs} } OPTIONAL,
        ...
}

TRPItem-ExtIEs NRPPA-PROTOCOL-EXTENSION ::= {
    ...
}

TRP-ID ::= INTEGER (1.. maxnoTRPs, ...)


TRPPositionDefinitionType ::= CHOICE {
    direct      TRPPositionDirect,
    referenced TRPPositionReferenced,
    choice-extension                              ProtocolIE-Single-Container { { TRPPositionDefinitionType-ExtIEs } }
}

TRPPositionDefinitionType-ExtIEs NRPPA-PROTOCOL-IES ::= {
    ...




}


TRPPositionDirect ::= SEQUENCE {
    accuracy    TRPPositionDirectAccuracy,
    iE-extensions       ProtocolExtensionContainer { { TRPPositionDirect-ExtIEs } } OPTIONAL,
    ...
}

TRPPositionDirect-ExtIEs NRPPA-PROTOCOL-EXTENSION ::= {
    ...
}

TRPPositionDirectAccuracy ::= CHOICE {
    tRPPosition         NG-RANAccessPointPosition                       ,
    tRPHAposition       NGRANHighAccuracyAccessPointPosition    ,
    choice-extension            ProtocolIE-Single-Container { { TRPPositionDirectAccuracy-ExtIEs } }
}

TRPPositionDirectAccuracy-ExtIEs NRPPA-PROTOCOL-IES ::= {
    ...
}


TRPPositionReferenced ::= SEQUENCE {
    referencePoint                  ReferencePoint,
    referencePointType              TRPReferencePointType,
    iE-extensions                           ProtocolExtensionContainer { { TRPPositionReferenced-ExtIEs } }     OPTIONAL,
    ...
}

TRPPositionReferenced-ExtIEs NRPPA-PROTOCOL-EXTENSION ::= {
    ...
}

TRP-PRS-Information-List ::= SEQUENCE (SIZE(1.. maxnoPRSTRPs)) OF TRP-PRS-Information-List-Item

TRP-PRS-Information-List-Item ::= SEQUENCE {
        tRP-ID              TRP-ID,
        nR-PCI              NR-PCI,
        cGI-NR              CGI-NR                  OPTIONAL,
        pRSConfiguration                            PRSConfiguration,
        iE-Extensions   ProtocolExtensionContainer { { TRP-PRS-Information-List-Item-ExtIEs} } OPTIONAL,
        ...
}

TRP-PRS-Information-List-Item-ExtIEs NRPPA-PROTOCOL-EXTENSION ::= {
    ...
}

TRPReferencePointType ::= CHOICE {
    tRPPositionRelativeGeodetic            RelativeGeodeticLocation,
    tRPPositionRelativeCartesian           RelativeCartesianLocation,
    choice-extension                               ProtocolIE-Single-Container { { TRPReferencePointType-ExtIEs } }




}

TRPReferencePointType-ExtIEs NRPPA-PROTOCOL-IES ::= {
    ...
}

TRPTxTEGAssociation ::= SEQUENCE (SIZE(1.. maxnoTRPTEGs)) OF TRPTEGItem

TRPTEGItem ::= SEQUENCE {
        tRP-Tx-TEG-ID             INTEGER (0..7),
        dl-PRSResourceSetID       PRS-Resource-Set-ID,
        dl-PRSResourceID-List     SEQUENCE (SIZE(1.. maxPRS-ResourcesPerSet)) OF DLPRSResourceID-Item OPTIONAL,
    iE-Extensions                     ProtocolExtensionContainer { { TRPTEGItem-ExtIEs } } OPTIONAL,
    ...
}

TRPTEGItem-ExtIEs NRPPA-PROTOCOL-EXTENSION ::= {
    { ID id-TRPTxTimingErrorMargin          CRITICALITY ignore EXTENSION TimingErrorMargin   PRESENCE optional },
    ...
}

DLPRSResourceID-Item ::= SEQUENCE {
    dl-PRSResourceID        PRS-Resource-ID,
    iE-Extensions           ProtocolExtensionContainer { { DLPRSResource-Item-ExtIEs} } OPTIONAL,
    ...
}

DLPRSResource-Item-ExtIEs NRPPA-PROTOCOL-EXTENSION ::= {
    ...
}


TRPType ::= ENUMERATED {
    prsOnlyTP,
    srsOnlyRP,
    tp,
    rp,
    trp,
    ...
}


TypeOfError ::= ENUMERATED {
    not-understood,
    missing,
    ...
}

-- U

UARFCN ::= INTEGER (0..16383, ...)

UE-Measurement-ID ::= INTEGER (1..15, ..., 16..256)





UEReportingInformation::= SEQUENCE {
    reportingAmount             ENUMERATED {ma0, ma1, ma2, ma4, ma8, ma16, ma32, ma64},
    reportingInterval           ENUMERATED {none, one, two, four, eight, ten, sixteen, twenty, thirty-two, sixty-four, ...},
    iE-extensions           ProtocolExtensionContainer { { UEReportingInformation-ExtIEs } }    OPTIONAL,
    ...
}

UEReportingInformation-ExtIEs NRPPA-PROTOCOL-EXTENSION ::= {
    ...
}

UE-TEG-ReportingPeriodicity ::= ENUMERATED {
    ms160,
    ms320,
    ms1280,
    ms2560,
    ms61440,
    ms81920,
    ms368640,
    ms737280,
    ...
}

UETxTEGAssociationList ::= SEQUENCE (SIZE(1.. maxnoUETEGs)) OF UETxTEGAssociationItem

UETxTEGAssociationItem ::= SEQUENCE {
        uE-Tx-TEG-ID                INTEGER (0..7),
        posSRSResourceID-List       PosSRSResourceID-List,
        timeStamp                   TimeStamp,
        carrierFreq                 CarrierFreq             OPTIONAL,
    iE-Extensions                   ProtocolExtensionContainer { { UETxTEGAssociationItem-ExtIEs } } OPTIONAL,
    ...
}

UETxTEGAssociationItem-ExtIEs NRPPA-PROTOCOL-EXTENSION ::= {
    { ID id-UETxTimingErrorMargin           CRITICALITY ignore EXTENSION TimingErrorMargin   PRESENCE optional },
    ...
}

SRSResourceID-Item ::= SEQUENCE {
    sRSResourceID                   SRSResourceID,
    iE-Extensions           ProtocolExtensionContainer { { SRSResourceID-Item-ExtIEs} } OPTIONAL,
    ...
}

SRSResourceID-Item-ExtIEs NRPPA-PROTOCOL-EXTENSION ::= {
    ...
}

UE-TEG-Info-Request ::= ENUMERATED {onDemand, periodic, stop, ...}

UTRA-EcN0 ::= INTEGER (0..49, ...)

UTRA-RSCP ::= INTEGER (-5..91, ...)






UL-AoA ::= SEQUENCE {
    azimuthAoA                   INTEGER (0..3599),
    zenithAoA                    INTEGER (0..1799)               OPTIONAL,
    lCS-to-GCS-Translation   LCS-to-GCS-Translation      OPTIONAL,
    iE-extensions            ProtocolExtensionContainer { { UL-AoA-ExtIEs } }   OPTIONAL,
    ...
}

UL-AoA-ExtIEs NRPPA-PROTOCOL-EXTENSION ::= {
    ...
}


UL-RTOAMeasurement ::= SEQUENCE {
        uLRTOAmeas          ULRTOAMeas,
        additionalPathList AdditionalPathList OPTIONAL,
    iE-extensions           ProtocolExtensionContainer { { UL-RTOAMeasurement-ExtIEs } }    OPTIONAL,   ...
}

UL-RTOAMeasurement-ExtIEs NRPPA-PROTOCOL-EXTENSION ::= {
    { ID id-ExtendedAdditionalPathList CRITICALITY ignore EXTENSION ExtendedAdditionalPathList PRESENCE optional}|
    { ID id-TRPRXTEGID                  CRITICALITY ignore EXTENSION    INTEGER (0..31)        PRESENCE optional}|
    { ID id-TRPRxTimingErrorMargin      CRITICALITY ignore EXTENSION TimingErrorMargin         PRESENCE optional },
    ...
}

ULRTOAMeas::= CHOICE {
    k0      INTEGER (0.. 1970049),
    k1      INTEGER (0.. 985025),
    k2      INTEGER (0.. 492513),
    k3      INTEGER (0.. 246257),
    k4      INTEGER (0.. 123129),
    k5      INTEGER (0.. 61565),
    choice-extension        ProtocolIE-Single-Container { { ULRTOAMeas-ExtIEs } }
}
ULRTOAMeas-ExtIEs NRPPA-PROTOCOL-IES ::= {
    ...
}

UL-SRS-RSRP ::= INTEGER (0..126)

UL-SRS-RSRPP ::= SEQUENCE {
    firstPathRSRPP              INTEGER (0..126),
    iE-extensions           ProtocolExtensionContainer { { UL-SRS-RSRPP-ExtIEs } }   OPTIONAL,
    ...
}

UL-SRS-RSRPP-ExtIEs NRPPA-PROTOCOL-EXTENSION ::= {
    ...
}

UplinkChannelBW-PerSCS-List ::= SEQUENCE (SIZE (1..maxnoSCSs)) OF SCS-SpecificCarrier






Uncertainty-range-AoA ::= INTEGER (0..3599)

Uncertainty-range-ZoA ::= INTEGER (0..1799)


-- V

ValueRSRP-EUTRA ::= INTEGER (0..97, ...)

ValueRSRQ-EUTRA ::= INTEGER (0..34, ...)

ValueRSRP-NR ::= INTEGER (0..127)

ValueRSRQ-NR ::= INTEGER (0..127)


-- W

WLANMeasurementQuantities ::= SEQUENCE (SIZE (0.. maxNoMeas)) OF ProtocolIE-Single-Container { {WLANMeasurementQuantities-ItemIEs} }

WLANMeasurementQuantities-ItemIEs NRPPA-PROTOCOL-IES ::= {
    { ID id-WLANMeasurementQuantities-Item CRITICALITY reject   TYPE WLANMeasurementQuantities-Item PRESENCE mandatory}}

WLANMeasurementQuantities-Item ::= SEQUENCE {
    wLANMeasurementQuantitiesValue          WLANMeasurementQuantitiesValue,
    iE-Extensions                           ProtocolExtensionContainer { { WLANMeasurementQuantitiesValue-ExtIEs} } OPTIONAL,
    ...
}

WLANMeasurementQuantitiesValue-ExtIEs NRPPA-PROTOCOL-EXTENSION ::= {
    ...
}

WLANMeasurementQuantitiesValue ::= ENUMERATED {
    wlan,
    ...
}

WLANMeasurementResult ::= SEQUENCE (SIZE (1..maxNoMeas)) OF WLANMeasurementResult-Item

WLANMeasurementResult-Item ::= SEQUENCE {
    wLAN-RSSI           WLAN-RSSI,
    sSID                SSID                    OPTIONAL,
    bSSID               BSSID                   OPTIONAL,
    hESSID              HESSID                  OPTIONAL,
    operatingClass      WLANOperatingClass      OPTIONAL,
    countryCode         WLANCountryCode         OPTIONAL,
    wLANChannelList     WLANChannelList         OPTIONAL,
    wLANBand            WLANBand                OPTIONAL,
    iE-Extensions       ProtocolExtensionContainer { { WLANMeasurementResult-Item-ExtIEs } }   OPTIONAL,
    ...
}





WLANMeasurementResult-Item-ExtIEs     NRPPA-PROTOCOL-EXTENSION ::= {
    ...
}

WLAN-RSSI ::= INTEGER (0..141, ...)

WLANBand ::= ENUMERATED {band2dot4, band5, ...}

WLANChannelList ::= SEQUENCE (SIZE (1..maxWLANchannels)) OF WLANChannel

WLANChannel ::= INTEGER (0..255)

WLANCountryCode ::= ENUMERATED {
    unitedStates,
    europe,
    japan,
    global,
    ...
}

WLANOperatingClass ::= INTEGER (0..255)

-- X

-- Y

-- Z

ZoA ::= SEQUENCE {
    zenithAoA                    INTEGER (0..1799),
    lCS-to-GCS-Translation   LCS-to-GCS-Translation      OPTIONAL,
    iE-extensions            ProtocolExtensionContainer { { ZoA-ExtIEs } }       OPTIONAL,
    ...
}

ZoA-ExtIEs NRPPA-PROTOCOL-EXTENSION ::= {
    ...
}


END
