-- ASN1START
-- **************************************************************
--
-- Elementary Procedure definitions
--
-- **************************************************************

NGAP-PDU-Descriptions  { 
itu-t (0) identified-organization (4) etsi (0) mobileDomain (0) 
ngran-Access (22) modules (3) ngap (1) version1 (1) ngap-PDU-Descriptions (0)}

DEFINITIONS AUTOMATIC TAGS ::= 

BEGIN

-- **************************************************************
--
-- IE parameter types from other modules.
--
-- **************************************************************

IMPORTS

	Criticality,
	ProcedureCode
FROM NGAP-CommonDataTypes

	AMFConfigurationUpdate,
	AMFConfigurationUpdateAcknowledge,
	AMFConfigurationUpdateFailure,
	AMFCPRelocationIndication,
	AMFStatusIndication,
	CellTrafficTrace,
	ConnectionEstablishmentIndication,
	DeactivateTrace,
	DownlinkNASTransport,
	DownlinkNonUEAssociatedNRPPaTransport,
	DownlinkRANConfigurationTransfer,
	DownlinkRANEarlyStatusTransfer,
	DownlinkRANStatusTransfer,
	DownlinkUEAssociatedNRPPaTransport,
	ErrorIndication,
	HandoverCancel,
	HandoverCancelAcknowledge,
	HandoverCommand,
	HandoverFailure,
	HandoverNotify,
	HandoverPreparationFailure,
	HandoverRequest,
	HandoverRequestAcknowledge,
	HandoverRequired,
	HandoverSuccess,
	InitialContextSetupFailure,
	InitialContextSetupRequest,
	InitialContextSetupResponse,
	InitialUEMessage,
	LocationReport,
	LocationReportingControl,
	LocationReportingFailureIndication,
	NASNonDeliveryIndication,
	NGReset,
	NGResetAcknowledge,
	NGSetupFailure,
	NGSetupRequest,
	NGSetupResponse,
	OverloadStart,
	OverloadStop,
	Paging,
	PathSwitchRequest,
	PathSwitchRequestAcknowledge,
	PathSwitchRequestFailure,	
	PDUSessionResourceModifyConfirm,
	PDUSessionResourceModifyIndication,
	PDUSessionResourceModifyRequest,
	PDUSessionResourceModifyResponse,
	PDUSessionResourceNotify,
	PDUSessionResourceReleaseCommand,
	PDUSessionResourceReleaseResponse,
	PDUSessionResourceSetupRequest,
	PDUSessionResourceSetupResponse,
	PrivateMessage,
	PWSCancelRequest,
	PWSCancelResponse,
	PWSFailureIndication,
	PWSRestartIndication,
	RANConfigurationUpdate,
	RANConfigurationUpdateAcknowledge,
	RANConfigurationUpdateFailure,
	RANCPRelocationIndication,
	RerouteNASRequest,
	RetrieveUEInformation,
	RRCInactiveTransitionReport,
	SecondaryRATDataUsageReport,
	TraceFailureIndication,
	TraceStart,
	UEContextModificationFailure,
	UEContextModificationRequest,
	UEContextModificationResponse,
	UEContextReleaseCommand,
	UEContextReleaseComplete,
	UEContextReleaseRequest,
	UEContextResumeRequest,
	UEContextResumeResponse,
	UEContextResumeFailure,
	UEContextSuspendRequest,
	UEContextSuspendResponse,
	UEContextSuspendFailure,
	UEInformationTransfer,
	UERadioCapabilityCheckRequest,
	UERadioCapabilityCheckResponse,
	UERadioCapabilityIDMappingRequest,
	UERadioCapabilityIDMappingResponse,
	UERadioCapabilityInfoIndication,
	UETNLABindingReleaseRequest,
	UplinkNASTransport,
	UplinkNonUEAssociatedNRPPaTransport,
	UplinkRANConfigurationTransfer,
	UplinkRANEarlyStatusTransfer,
	UplinkRANStatusTransfer,
	UplinkUEAssociatedNRPPaTransport,
	WriteReplaceWarningRequest,
	WriteReplaceWarningResponse,
	UplinkRIMInformationTransfer,
	DownlinkRIMInformationTransfer

FROM NGAP-PDU-Contents

	id-AMFConfigurationUpdate,
	id-AMFCPRelocationIndication,
	id-AMFStatusIndication,
	id-CellTrafficTrace,
	id-ConnectionEstablishmentIndication,
	id-DeactivateTrace,
	id-DownlinkNASTransport,
	id-DownlinkNonUEAssociatedNRPPaTransport,
	id-DownlinkRANConfigurationTransfer,
	id-DownlinkRANEarlyStatusTransfer,
	id-DownlinkRANStatusTransfer,
	id-DownlinkUEAssociatedNRPPaTransport,
	id-ErrorIndication,
	id-HandoverCancel,
	id-HandoverNotification,
	id-HandoverPreparation,
	id-HandoverResourceAllocation,
	id-HandoverSuccess,
	id-InitialContextSetup,
	id-InitialUEMessage,
	id-LocationReport,
	id-LocationReportingControl,
	id-LocationReportingFailureIndication,
	id-NASNonDeliveryIndication,
	id-NGReset,
	id-NGSetup,
	id-OverloadStart,
	id-OverloadStop,
	id-Paging,
	id-PathSwitchRequest,
	id-PDUSessionResourceModify,
	id-PDUSessionResourceModifyIndication,
	id-PDUSessionResourceNotify,
	id-PDUSessionResourceRelease,
	id-PDUSessionResourceSetup,
	id-PrivateMessage,
	id-PWSCancel,
	id-PWSFailureIndication,
	id-PWSRestartIndication,
	id-RANConfigurationUpdate,
	id-RANCPRelocationIndication,
	id-RerouteNASRequest,
	id-RetrieveUEInformation,
	id-RRCInactiveTransitionReport,
	id-SecondaryRATDataUsageReport,
	id-TraceFailureIndication,
	id-TraceStart,
	id-UEContextModification,
	id-UEContextRelease,
	id-UEContextReleaseRequest,
	id-UEContextResume,
	id-UEContextSuspend,
	id-UEInformationTransfer,
	id-UERadioCapabilityCheck,
	id-UERadioCapabilityIDMapping,
	id-UERadioCapabilityInfoIndication,
	id-UETNLABindingRelease,
	id-UplinkNASTransport,
	id-UplinkNonUEAssociatedNRPPaTransport,
	id-UplinkRANConfigurationTransfer,
	id-UplinkRANEarlyStatusTransfer,
	id-UplinkRANStatusTransfer,
	id-UplinkUEAssociatedNRPPaTransport,
	id-WriteReplaceWarning,
	id-UplinkRIMInformationTransfer,
	id-DownlinkRIMInformationTransfer

FROM NGAP-Constants;

-- **************************************************************
--
-- Interface Elementary Procedure Class
--
-- **************************************************************

NGAP-ELEMENTARY-PROCEDURE ::= CLASS {
	&InitiatingMessage				,
	&SuccessfulOutcome							OPTIONAL,
	&UnsuccessfulOutcome						OPTIONAL,
	&procedureCode				ProcedureCode	UNIQUE,
	&criticality				Criticality	DEFAULT ignore
}

WITH SYNTAX {
	INITIATING MESSAGE			&InitiatingMessage
	[SUCCESSFUL OUTCOME			&SuccessfulOutcome]
	[UNSUCCESSFUL OUTCOME		&UnsuccessfulOutcome]
	PROCEDURE CODE				&procedureCode
	[CRITICALITY				&criticality]
}

-- **************************************************************
--
-- Interface PDU Definition
--
-- **************************************************************

NGAP-PDU ::= CHOICE {
	initiatingMessage			InitiatingMessage,
	successfulOutcome			SuccessfulOutcome,
	unsuccessfulOutcome			UnsuccessfulOutcome,
	...
}

InitiatingMessage ::= SEQUENCE {
	procedureCode	NGAP-ELEMENTARY-PROCEDURE.&procedureCode		({NGAP-ELEMENTARY-PROCEDURES}),
	criticality		NGAP-ELEMENTARY-PROCEDURE.&criticality			({NGAP-ELEMENTARY-PROCEDURES}{@procedureCode}),
	value			NGAP-ELEMENTARY-PROCEDURE.&InitiatingMessage	({NGAP-ELEMENTARY-PROCEDURES}{@procedureCode})
}

SuccessfulOutcome ::= SEQUENCE {
	procedureCode	NGAP-ELEMENTARY-PROCEDURE.&procedureCode		({NGAP-ELEMENTARY-PROCEDURES}),
	criticality		NGAP-ELEMENTARY-PROCEDURE.&criticality			({NGAP-ELEMENTARY-PROCEDURES}{@procedureCode}),
	value			NGAP-ELEMENTARY-PROCEDURE.&SuccessfulOutcome	({NGAP-ELEMENTARY-PROCEDURES}{@procedureCode})
}

UnsuccessfulOutcome ::= SEQUENCE {
	procedureCode	NGAP-ELEMENTARY-PROCEDURE.&procedureCode		({NGAP-ELEMENTARY-PROCEDURES}),
	criticality		NGAP-ELEMENTARY-PROCEDURE.&criticality			({NGAP-ELEMENTARY-PROCEDURES}{@procedureCode}),
	value			NGAP-ELEMENTARY-PROCEDURE.&UnsuccessfulOutcome	({NGAP-ELEMENTARY-PROCEDURES}{@procedureCode})
}

-- **************************************************************
--
-- Interface Elementary Procedure List
--
-- **************************************************************

NGAP-ELEMENTARY-PROCEDURES NGAP-ELEMENTARY-PROCEDURE ::= {
	NGAP-ELEMENTARY-PROCEDURES-CLASS-1			|
	NGAP-ELEMENTARY-PROCEDURES-CLASS-2,	
	...
}

NGAP-ELEMENTARY-PROCEDURES-CLASS-1 NGAP-ELEMENTARY-PROCEDURE ::= {
	aMFConfigurationUpdate			|
	handoverCancel					|
	handoverPreparation				|
	handoverResourceAllocation		|
	initialContextSetup				|
	nGReset							|
	nGSetup							|
	pathSwitchRequest				|
	pDUSessionResourceModify		|
	pDUSessionResourceModifyIndication			|
	pDUSessionResourceRelease		|
	pDUSessionResourceSetup			|
	pWSCancel						|
	rANConfigurationUpdate			|
	uEContextModification			|
	uEContextRelease				|
	uEContextResume								|
	uEContextSuspend							|
	uERadioCapabilityCheck			|
	uERadioCapabilityIDMapping		|
	writeReplaceWarning,
	...
}

NGAP-ELEMENTARY-PROCEDURES-CLASS-2 NGAP-ELEMENTARY-PROCEDURE ::= {	
	aMFCPRelocationIndication		|
	aMFStatusIndication				|
	cellTrafficTrace				|
	connectionEstablishmentIndication	|
	deactivateTrace					|
	downlinkNASTransport			|
	downlinkNonUEAssociatedNRPPaTransport	|
	downlinkRANConfigurationTransfer	|
	downlinkRANEarlyStatusTransfer	|
	downlinkRANStatusTransfer		|
	downlinkRIMInformationTransfer	|
	downlinkUEAssociatedNRPPaTransport	|
	errorIndication					|
	handoverNotification			|
	handoverSuccess								|
	initialUEMessage				|
	locationReport					|
	locationReportingControl		|
	locationReportingFailureIndication	|
	nASNonDeliveryIndication		|
	overloadStart					|
	overloadStop					|
	paging							|
	pDUSessionResourceNotify		|
	privateMessage					|
	pWSFailureIndication						|
	pWSRestartIndication			|
	rANCPRelocationIndication		|
	rerouteNASRequest				|
	retrieveUEInformation						|
	rRCInactiveTransitionReport					|
	secondaryRATDataUsageReport		|
	traceFailureIndication			|
	traceStart						|
	uEContextReleaseRequest			|
	uEInformationTransfer						|
	uERadioCapabilityInfoIndication	|
	uETNLABindingRelease			|
	uplinkNASTransport				|
	uplinkNonUEAssociatedNRPPaTransport	|
	uplinkRANConfigurationTransfer	|
	uplinkRANEarlyStatusTransfer				|
	uplinkRANStatusTransfer			|
	uplinkRIMInformationTransfer				|
	uplinkUEAssociatedNRPPaTransport,
	...

}

-- **************************************************************
--
-- Interface Elementary Procedures
--
-- **************************************************************

aMFConfigurationUpdate NGAP-ELEMENTARY-PROCEDURE ::= {
	INITIATING MESSAGE		AMFConfigurationUpdate
	SUCCESSFUL OUTCOME		AMFConfigurationUpdateAcknowledge
	UNSUCCESSFUL OUTCOME	AMFConfigurationUpdateFailure
	PROCEDURE CODE			id-AMFConfigurationUpdate
	CRITICALITY				reject
}

aMFCPRelocationIndication NGAP-ELEMENTARY-PROCEDURE ::= {
	INITIATING MESSAGE		AMFCPRelocationIndication
	PROCEDURE CODE			id-AMFCPRelocationIndication
	CRITICALITY				reject
}

aMFStatusIndication NGAP-ELEMENTARY-PROCEDURE ::={
	INITIATING MESSAGE		AMFStatusIndication
	PROCEDURE CODE			id-AMFStatusIndication
	CRITICALITY				ignore
}

cellTrafficTrace NGAP-ELEMENTARY-PROCEDURE ::={
	INITIATING MESSAGE		CellTrafficTrace
	PROCEDURE CODE			id-CellTrafficTrace
	CRITICALITY				ignore
}

connectionEstablishmentIndication NGAP-ELEMENTARY-PROCEDURE ::= {
	INITIATING MESSAGE		ConnectionEstablishmentIndication
	PROCEDURE CODE			id-ConnectionEstablishmentIndication
	CRITICALITY				reject
}

deactivateTrace NGAP-ELEMENTARY-PROCEDURE ::= {
	INITIATING MESSAGE		DeactivateTrace
	PROCEDURE CODE			id-DeactivateTrace
	CRITICALITY				ignore
}

downlinkNASTransport NGAP-ELEMENTARY-PROCEDURE ::= {
	INITIATING MESSAGE		DownlinkNASTransport
	PROCEDURE CODE			id-DownlinkNASTransport
	CRITICALITY				ignore
}

downlinkNonUEAssociatedNRPPaTransport NGAP-ELEMENTARY-PROCEDURE ::= {
	INITIATING MESSAGE		DownlinkNonUEAssociatedNRPPaTransport
	PROCEDURE CODE			id-DownlinkNonUEAssociatedNRPPaTransport
	CRITICALITY				ignore
}

downlinkRANConfigurationTransfer NGAP-ELEMENTARY-PROCEDURE ::= {
	INITIATING MESSAGE		DownlinkRANConfigurationTransfer
	PROCEDURE CODE			id-DownlinkRANConfigurationTransfer
	CRITICALITY				ignore
}

downlinkRANEarlyStatusTransfer NGAP-ELEMENTARY-PROCEDURE ::= {
	INITIATING MESSAGE		DownlinkRANEarlyStatusTransfer
	PROCEDURE CODE			id-DownlinkRANEarlyStatusTransfer
	CRITICALITY				ignore
}

downlinkRANStatusTransfer NGAP-ELEMENTARY-PROCEDURE ::= {
	INITIATING MESSAGE		DownlinkRANStatusTransfer
	PROCEDURE CODE			id-DownlinkRANStatusTransfer
	CRITICALITY				ignore
}

downlinkUEAssociatedNRPPaTransport NGAP-ELEMENTARY-PROCEDURE ::= {
	INITIATING MESSAGE		DownlinkUEAssociatedNRPPaTransport
	PROCEDURE CODE			id-DownlinkUEAssociatedNRPPaTransport
	CRITICALITY				ignore
}

errorIndication NGAP-ELEMENTARY-PROCEDURE ::= {
	INITIATING MESSAGE		ErrorIndication
	PROCEDURE CODE			id-ErrorIndication
	CRITICALITY				ignore
}

handoverCancel NGAP-ELEMENTARY-PROCEDURE ::= {
	INITIATING MESSAGE		HandoverCancel
	SUCCESSFUL OUTCOME		HandoverCancelAcknowledge
	PROCEDURE CODE			id-HandoverCancel
	CRITICALITY				reject
}

handoverNotification NGAP-ELEMENTARY-PROCEDURE ::= {
	INITIATING MESSAGE		HandoverNotify
	PROCEDURE CODE			id-HandoverNotification
	CRITICALITY				ignore
}

handoverPreparation NGAP-ELEMENTARY-PROCEDURE ::= {
	INITIATING MESSAGE		HandoverRequired
	SUCCESSFUL OUTCOME		HandoverCommand
	UNSUCCESSFUL OUTCOME	HandoverPreparationFailure
	PROCEDURE CODE			id-HandoverPreparation
	CRITICALITY				reject
}

handoverResourceAllocation NGAP-ELEMENTARY-PROCEDURE ::= {
	INITIATING MESSAGE		HandoverRequest
	SUCCESSFUL OUTCOME		HandoverRequestAcknowledge
	UNSUCCESSFUL OUTCOME	HandoverFailure
	PROCEDURE CODE			id-HandoverResourceAllocation
	CRITICALITY				reject
}

handoverSuccess NGAP-ELEMENTARY-PROCEDURE ::= {
	INITIATING MESSAGE		HandoverSuccess
	PROCEDURE CODE			id-HandoverSuccess
	CRITICALITY				ignore
}

initialContextSetup NGAP-ELEMENTARY-PROCEDURE ::= {
	INITIATING MESSAGE		InitialContextSetupRequest
	SUCCESSFUL OUTCOME		InitialContextSetupResponse
	UNSUCCESSFUL OUTCOME	InitialContextSetupFailure
	PROCEDURE CODE			id-InitialContextSetup
	CRITICALITY				reject
}

initialUEMessage NGAP-ELEMENTARY-PROCEDURE ::= {
	INITIATING MESSAGE		InitialUEMessage
	PROCEDURE CODE			id-InitialUEMessage
	CRITICALITY				ignore
}

locationReport NGAP-ELEMENTARY-PROCEDURE ::= {
	INITIATING MESSAGE		LocationReport
	PROCEDURE CODE			id-LocationReport
	CRITICALITY				ignore
}

locationReportingControl NGAP-ELEMENTARY-PROCEDURE ::= {
	INITIATING MESSAGE		LocationReportingControl
	PROCEDURE CODE			id-LocationReportingControl
	CRITICALITY				ignore
}

locationReportingFailureIndication NGAP-ELEMENTARY-PROCEDURE ::= {
	INITIATING MESSAGE		LocationReportingFailureIndication
	PROCEDURE CODE			id-LocationReportingFailureIndication
	CRITICALITY				ignore
}

nASNonDeliveryIndication NGAP-ELEMENTARY-PROCEDURE ::= {
	INITIATING MESSAGE		NASNonDeliveryIndication
	PROCEDURE CODE			id-NASNonDeliveryIndication
	CRITICALITY				ignore
}

nGReset NGAP-ELEMENTARY-PROCEDURE ::= {
	INITIATING MESSAGE		NGReset
	SUCCESSFUL OUTCOME		NGResetAcknowledge
	PROCEDURE CODE			id-NGReset
	CRITICALITY				reject
}

nGSetup NGAP-ELEMENTARY-PROCEDURE ::= {
	INITIATING MESSAGE		NGSetupRequest
	SUCCESSFUL OUTCOME		NGSetupResponse
	UNSUCCESSFUL OUTCOME	NGSetupFailure
	PROCEDURE CODE			id-NGSetup
	CRITICALITY				reject
}

overloadStart NGAP-ELEMENTARY-PROCEDURE ::= {
	INITIATING MESSAGE		OverloadStart
	PROCEDURE CODE			id-OverloadStart
	CRITICALITY				ignore
}

overloadStop NGAP-ELEMENTARY-PROCEDURE ::= {
	INITIATING MESSAGE		OverloadStop
	PROCEDURE CODE			id-OverloadStop
	CRITICALITY				reject
}

paging NGAP-ELEMENTARY-PROCEDURE ::= {
	INITIATING MESSAGE		Paging
	PROCEDURE CODE			id-Paging
	CRITICALITY				ignore
}

pathSwitchRequest NGAP-ELEMENTARY-PROCEDURE ::= {
	INITIATING MESSAGE		PathSwitchRequest
	SUCCESSFUL OUTCOME		PathSwitchRequestAcknowledge
	UNSUCCESSFUL OUTCOME	PathSwitchRequestFailure
	PROCEDURE CODE			id-PathSwitchRequest
	CRITICALITY				reject
}

pDUSessionResourceModify NGAP-ELEMENTARY-PROCEDURE ::= {
	INITIATING MESSAGE		PDUSessionResourceModifyRequest
	SUCCESSFUL OUTCOME		PDUSessionResourceModifyResponse
	PROCEDURE CODE			id-PDUSessionResourceModify
	CRITICALITY				reject
}

pDUSessionResourceModifyIndication NGAP-ELEMENTARY-PROCEDURE ::= {
	INITIATING MESSAGE		PDUSessionResourceModifyIndication
	SUCCESSFUL OUTCOME		PDUSessionResourceModifyConfirm
	PROCEDURE CODE			id-PDUSessionResourceModifyIndication
	CRITICALITY				reject
}

pDUSessionResourceNotify NGAP-ELEMENTARY-PROCEDURE ::= {
	INITIATING MESSAGE		PDUSessionResourceNotify
	PROCEDURE CODE			id-PDUSessionResourceNotify
	CRITICALITY				ignore
}

pDUSessionResourceRelease NGAP-ELEMENTARY-PROCEDURE ::= {
	INITIATING MESSAGE		PDUSessionResourceReleaseCommand
	SUCCESSFUL OUTCOME		PDUSessionResourceReleaseResponse
	PROCEDURE CODE			id-PDUSessionResourceRelease
	CRITICALITY				reject
}

pDUSessionResourceSetup NGAP-ELEMENTARY-PROCEDURE ::= {
	INITIATING MESSAGE		PDUSessionResourceSetupRequest
	SUCCESSFUL OUTCOME		PDUSessionResourceSetupResponse
	PROCEDURE CODE			id-PDUSessionResourceSetup
	CRITICALITY				reject
}

privateMessage NGAP-ELEMENTARY-PROCEDURE ::= {
	INITIATING MESSAGE		PrivateMessage
	PROCEDURE CODE			id-PrivateMessage
	CRITICALITY				ignore
}

pWSCancel NGAP-ELEMENTARY-PROCEDURE ::= {
	INITIATING MESSAGE		PWSCancelRequest
	SUCCESSFUL OUTCOME		PWSCancelResponse
	PROCEDURE CODE			id-PWSCancel
	CRITICALITY				reject
}

pWSFailureIndication NGAP-ELEMENTARY-PROCEDURE ::= {
	INITIATING MESSAGE		PWSFailureIndication
	PROCEDURE CODE			id-PWSFailureIndication
	CRITICALITY				ignore
}

pWSRestartIndication NGAP-ELEMENTARY-PROCEDURE ::= {
	INITIATING MESSAGE		PWSRestartIndication
	PROCEDURE CODE			id-PWSRestartIndication
	CRITICALITY				ignore
}

rANConfigurationUpdate NGAP-ELEMENTARY-PROCEDURE ::= {
	INITIATING MESSAGE		RANConfigurationUpdate
	SUCCESSFUL OUTCOME		RANConfigurationUpdateAcknowledge
	UNSUCCESSFUL OUTCOME	RANConfigurationUpdateFailure
	PROCEDURE CODE			id-RANConfigurationUpdate
	CRITICALITY				reject
}

rANCPRelocationIndication NGAP-ELEMENTARY-PROCEDURE ::= {
	INITIATING MESSAGE		RANCPRelocationIndication
	PROCEDURE CODE			id-RANCPRelocationIndication
	CRITICALITY				reject
}

rerouteNASRequest NGAP-ELEMENTARY-PROCEDURE ::= {
	INITIATING MESSAGE		RerouteNASRequest
	PROCEDURE CODE			id-RerouteNASRequest
	CRITICALITY				reject
}


retrieveUEInformation NGAP-ELEMENTARY-PROCEDURE ::= {
	INITIATING MESSAGE		RetrieveUEInformation
	PROCEDURE CODE			id-RetrieveUEInformation
	CRITICALITY				reject
}

rRCInactiveTransitionReport NGAP-ELEMENTARY-PROCEDURE ::= {
	INITIATING MESSAGE		RRCInactiveTransitionReport
	PROCEDURE CODE			id-RRCInactiveTransitionReport
	CRITICALITY				ignore
}

secondaryRATDataUsageReport NGAP-ELEMENTARY-PROCEDURE ::= {
	INITIATING MESSAGE		SecondaryRATDataUsageReport
	PROCEDURE CODE			id-SecondaryRATDataUsageReport
	CRITICALITY				ignore
}

traceFailureIndication NGAP-ELEMENTARY-PROCEDURE ::= {
	INITIATING MESSAGE		TraceFailureIndication
	PROCEDURE CODE			id-TraceFailureIndication
	CRITICALITY				ignore
}

traceStart NGAP-ELEMENTARY-PROCEDURE ::= {
	INITIATING MESSAGE		TraceStart
	PROCEDURE CODE			id-TraceStart
	CRITICALITY				ignore
}

uEContextModification NGAP-ELEMENTARY-PROCEDURE ::= {
	INITIATING MESSAGE		UEContextModificationRequest
	SUCCESSFUL OUTCOME		UEContextModificationResponse
	UNSUCCESSFUL OUTCOME	UEContextModificationFailure
	PROCEDURE CODE			id-UEContextModification
	CRITICALITY				reject
}

uEContextRelease NGAP-ELEMENTARY-PROCEDURE ::= {
	INITIATING MESSAGE		UEContextReleaseCommand
	SUCCESSFUL OUTCOME		UEContextReleaseComplete
	PROCEDURE CODE			id-UEContextRelease
	CRITICALITY				reject
}

uEContextReleaseRequest NGAP-ELEMENTARY-PROCEDURE ::= {
	INITIATING MESSAGE		UEContextReleaseRequest
	PROCEDURE CODE			id-UEContextReleaseRequest
	CRITICALITY				ignore
}

uEContextResume NGAP-ELEMENTARY-PROCEDURE ::= {
	INITIATING MESSAGE		UEContextResumeRequest
	SUCCESSFUL OUTCOME		UEContextResumeResponse
	UNSUCCESSFUL OUTCOME	UEContextResumeFailure
	PROCEDURE CODE			id-UEContextResume
	CRITICALITY				reject
}

uEContextSuspend NGAP-ELEMENTARY-PROCEDURE ::= {
	INITIATING MESSAGE		UEContextSuspendRequest
	SUCCESSFUL OUTCOME		UEContextSuspendResponse
	UNSUCCESSFUL OUTCOME	UEContextSuspendFailure
	PROCEDURE CODE			id-UEContextSuspend
	CRITICALITY				reject
}

uEInformationTransfer NGAP-ELEMENTARY-PROCEDURE ::= {
	INITIATING MESSAGE		UEInformationTransfer
	PROCEDURE CODE			id-UEInformationTransfer
	CRITICALITY				reject
}

uERadioCapabilityCheck NGAP-ELEMENTARY-PROCEDURE ::= {
	INITIATING MESSAGE		UERadioCapabilityCheckRequest
	SUCCESSFUL OUTCOME		UERadioCapabilityCheckResponse
	PROCEDURE CODE			id-UERadioCapabilityCheck
	CRITICALITY				reject
}

uERadioCapabilityIDMapping NGAP-ELEMENTARY-PROCEDURE ::= {
	INITIATING MESSAGE		UERadioCapabilityIDMappingRequest
	SUCCESSFUL OUTCOME		UERadioCapabilityIDMappingResponse
	PROCEDURE CODE			id-UERadioCapabilityIDMapping
	CRITICALITY				reject
}

uERadioCapabilityInfoIndication NGAP-ELEMENTARY-PROCEDURE ::= {
	INITIATING MESSAGE		UERadioCapabilityInfoIndication
	PROCEDURE CODE			id-UERadioCapabilityInfoIndication
	CRITICALITY				ignore
}

uETNLABindingRelease NGAP-ELEMENTARY-PROCEDURE ::= {
	INITIATING MESSAGE		UETNLABindingReleaseRequest
	PROCEDURE CODE			id-UETNLABindingRelease
	CRITICALITY				ignore
}

uplinkNASTransport NGAP-ELEMENTARY-PROCEDURE ::= {
	INITIATING MESSAGE		UplinkNASTransport
	PROCEDURE CODE			id-UplinkNASTransport
	CRITICALITY				ignore
}

uplinkNonUEAssociatedNRPPaTransport NGAP-ELEMENTARY-PROCEDURE ::= {
	INITIATING MESSAGE		UplinkNonUEAssociatedNRPPaTransport
	PROCEDURE CODE			id-UplinkNonUEAssociatedNRPPaTransport
	CRITICALITY				ignore
}

uplinkRANConfigurationTransfer NGAP-ELEMENTARY-PROCEDURE ::= {
	INITIATING MESSAGE		UplinkRANConfigurationTransfer
	PROCEDURE CODE			id-UplinkRANConfigurationTransfer
	CRITICALITY				ignore
}

uplinkRANEarlyStatusTransfer NGAP-ELEMENTARY-PROCEDURE ::= {
	INITIATING MESSAGE		UplinkRANEarlyStatusTransfer
	PROCEDURE CODE			id-UplinkRANEarlyStatusTransfer
	CRITICALITY				reject
}

uplinkRANStatusTransfer NGAP-ELEMENTARY-PROCEDURE ::= {
	INITIATING MESSAGE		UplinkRANStatusTransfer
	PROCEDURE CODE			id-UplinkRANStatusTransfer
	CRITICALITY				ignore
}

uplinkUEAssociatedNRPPaTransport NGAP-ELEMENTARY-PROCEDURE ::= {
	INITIATING MESSAGE		UplinkUEAssociatedNRPPaTransport
	PROCEDURE CODE			id-UplinkUEAssociatedNRPPaTransport
	CRITICALITY				ignore
}

writeReplaceWarning NGAP-ELEMENTARY-PROCEDURE ::= {
	INITIATING MESSAGE		WriteReplaceWarningRequest
	SUCCESSFUL OUTCOME		WriteReplaceWarningResponse
	PROCEDURE CODE			id-WriteReplaceWarning
	CRITICALITY				reject
}

uplinkRIMInformationTransfer NGAP-ELEMENTARY-PROCEDURE ::= {
	INITIATING MESSAGE		UplinkRIMInformationTransfer
	PROCEDURE CODE			id-UplinkRIMInformationTransfer
	CRITICALITY				ignore
}

downlinkRIMInformationTransfer NGAP-ELEMENTARY-PROCEDURE ::= {
	INITIATING MESSAGE		DownlinkRIMInformationTransfer
	PROCEDURE CODE			id-DownlinkRIMInformationTransfer
	CRITICALITY				ignore
}

END
-- ASN1STOP

-- ASN1START
-- **************************************************************
--
-- PDU definitions for NGAP.
--
-- **************************************************************

NGAP-PDU-Contents { 
itu-t (0) identified-organization (4) etsi (0) mobileDomain (0) 
ngran-Access (22) modules (3) ngap (1) version1 (1) ngap-PDU-Contents (1) }

DEFINITIONS AUTOMATIC TAGS ::= 

BEGIN

-- **************************************************************
--
-- IE parameter types from other modules.
--
-- **************************************************************

IMPORTS

	AllowedNSSAI,
	AMFName,
	AMFSetID,
	AMF-TNLAssociationSetupList,
	AMF-TNLAssociationToAddList,
	AMF-TNLAssociationToRemoveList,
	AMF-TNLAssociationToUpdateList,
	AMF-UE-NGAP-ID,
	AssistanceDataForPaging,
	AuthenticatedIndication,
	BroadcastCancelledAreaList,
	BroadcastCompletedAreaList,
	CancelAllWarningMessages,
	Cause,
	CellIDListForRestart,
	CEmodeBrestricted,
	CEmodeBSupport-Indicator,
	CNAssistedRANTuning,
	ConcurrentWarningMessageInd,
	CoreNetworkAssistanceInformationForInactive,
	CPTransportLayerInformation,
	CriticalityDiagnostics,
	DataCodingScheme,
	DL-CP-SecurityInformation,
	DirectForwardingPathAvailability,
	EarlyStatusTransfer-TransparentContainer,
	EDT-Session,
	EmergencyAreaIDListForRestart,
	EmergencyFallbackIndicator,
	EN-DCSONConfigurationTransfer,
	EndIndication,
	Enhanced-CoverageRestriction,
	EUTRA-CGI,
	Extended-AMFName,
	Extended-ConnectedTime,
	Extended-RANNodeName,
	FiveG-S-TMSI,
	GlobalRANNodeID,
	GUAMI,
	HandoverFlag,
	HandoverType,
	IAB-Authorized,
	IAB-Supported,
	IABNodeIndication,
	IMSVoiceSupportIndicator,
	IndexToRFSP,
	InfoOnRecommendedCellsAndRANNodesForPaging,
	IntersystemSONConfigurationTransfer,
	LAI,
	LTEM-Indication,
	LocationReportingRequestType,
	LTEUESidelinkAggregateMaximumBitrate,
	LTEV2XServicesAuthorized,
	MaskedIMEISV,
	MessageIdentifier,
	MDTPLMNList,
	MobilityRestrictionList,
	NAS-PDU,
	NASSecurityParametersFromNGRAN,
	NB-IoT-DefaultPagingDRX,
	NB-IoT-PagingDRX,
	NB-IoT-Paging-eDRXInfo,
	NB-IoT-UEPriority,
	NewSecurityContextInd,
	NGRAN-CGI,
	NGRAN-TNLAssociationToRemoveList,
	NGRANTraceID,
	NotifySourceNGRANNode,
	NPN-AccessInformation,
	NR-CGI,
	NRPPa-PDU,
	NumberOfBroadcastsRequested,
	NRUESidelinkAggregateMaximumBitrate,
	NRV2XServicesAuthorized,
	OverloadResponse,
	OverloadStartNSSAIList,
	PagingAssisDataforCEcapabUE,
	PagingDRX,
	PagingOrigin,
	PagingPriority,
	PagingeDRXInformation,
	PDUSessionAggregateMaximumBitRate,
	PDUSessionResourceAdmittedList,
	PDUSessionResourceFailedToModifyListModCfm,
	PDUSessionResourceFailedToModifyListModRes,
	PDUSessionResourceFailedToResumeListRESReq,
	PDUSessionResourceFailedToResumeListRESRes,
	PDUSessionResourceFailedToSetupListCxtFail,
	PDUSessionResourceFailedToSetupListCxtRes,
	PDUSessionResourceFailedToSetupListHOAck,
	PDUSessionResourceFailedToSetupListPSReq,
	PDUSessionResourceFailedToSetupListSURes,
	PDUSessionResourceHandoverList,
	PDUSessionResourceListCxtRelCpl,
	PDUSessionResourceListCxtRelReq,
	PDUSessionResourceListHORqd,
	PDUSessionResourceModifyListModCfm,
	PDUSessionResourceModifyListModInd,
	PDUSessionResourceModifyListModReq,
	PDUSessionResourceModifyListModRes,
	PDUSessionResourceNotifyList,
	PDUSessionResourceReleasedListNot,
	PDUSessionResourceReleasedListPSAck,
	PDUSessionResourceReleasedListPSFail,
	PDUSessionResourceReleasedListRelRes,
	PDUSessionResourceResumeListRESReq,
	PDUSessionResourceResumeListRESRes,
	PDUSessionResourceSecondaryRATUsageList,
	PDUSessionResourceSetupListCxtReq,
	PDUSessionResourceSetupListCxtRes,
	PDUSessionResourceSetupListHOReq,
	PDUSessionResourceSetupListSUReq,
	PDUSessionResourceSetupListSURes,
	PDUSessionResourceSuspendListSUSReq,
	PDUSessionResourceSwitchedList,
	PDUSessionResourceToBeSwitchedDLList,
	PDUSessionResourceToReleaseListHOCmd,
	PDUSessionResourceToReleaseListRelCmd,
	PLMNIdentity,
	PLMNSupportList,
	PrivacyIndicator,
	PWSFailedCellIDList,
	PC5QoSParameters,
	RANNodeName,
	RANPagingPriority,
	RANStatusTransfer-TransparentContainer,
	RAN-UE-NGAP-ID,
	RedirectionVoiceFallback,
	RelativeAMFCapacity,
	RepetitionPeriod,
	ResetType,
	RGLevelWirelineAccessCharacteristics,
	RoutingID,
	RRCEstablishmentCause,
	RRCInactiveTransitionReportRequest,
	RRCState,
	SecurityContext,
	SecurityKey,
	SerialNumber,
	ServedGUAMIList,
	SliceSupportList,
	S-NSSAI,
	SONConfigurationTransfer,
	SourceToTarget-TransparentContainer,
	SourceToTarget-AMFInformationReroute,
	SRVCCOperationPossible,
	SupportedTAList,
	Suspend-Request-Indication,
	Suspend-Response-Indication,
	TAI,
	TAIListForPaging,
	TAIListForRestart,
	TargetID,
	TargetToSource-TransparentContainer,
	TargettoSource-Failure-TransparentContainer,
	TimeToWait,
	TNLAssociationList,
	TraceActivation,
	TrafficLoadReductionIndication,
	TransportLayerAddress,
	UEAggregateMaximumBitRate,
	UE-associatedLogicalNG-connectionList,
	UECapabilityInfoRequest,
	UEContextRequest,
	UE-DifferentiationInfo,
	UE-NGAP-IDs,
	UEPagingIdentity,
	UEPresenceInAreaOfInterestList,
	UERadioCapability,
	UERadioCapabilityForPaging,
	UERadioCapabilityID,
	UERetentionInformation,
	UESecurityCapabilities,
	UE-UP-CIoT-Support,
	UL-CP-SecurityInformation,
	UnavailableGUAMIList,
	URI-address,
	UserLocationInformation,
	WarningAreaCoordinates,
	WarningAreaList,
	WarningMessageContents,
	WarningSecurityInfo,
	WarningType,
	WUS-Assistance-Information,
	RIMInformationTransfer

FROM NGAP-IEs

	PrivateIE-Container{},
	ProtocolExtensionContainer{},
	ProtocolIE-Container{},
	ProtocolIE-ContainerList{},
	ProtocolIE-ContainerPair{},
	ProtocolIE-SingleContainer{},
	NGAP-PRIVATE-IES,
	NGAP-PROTOCOL-EXTENSION,
	NGAP-PROTOCOL-IES,
	NGAP-PROTOCOL-IES-PAIR
FROM NGAP-Containers

	id-AllowedNSSAI,
	id-AMFName,
	id-AMFOverloadResponse,
	id-AMFSetID,
	id-AMF-TNLAssociationFailedToSetupList,
	id-AMF-TNLAssociationSetupList,
	id-AMF-TNLAssociationToAddList,
	id-AMF-TNLAssociationToRemoveList,
	id-AMF-TNLAssociationToUpdateList,
	id-AMFTrafficLoadReductionIndication,
	id-AMF-UE-NGAP-ID,
	id-AssistanceDataForPaging,
	id-AuthenticatedIndication,
	id-BroadcastCancelledAreaList,
	id-BroadcastCompletedAreaList,
	id-CancelAllWarningMessages,
	id-Cause,
	id-CellIDListForRestart,
	id-CEmodeBrestricted,
	id-CEmodeBSupport-Indicator,
	id-CNAssistedRANTuning,
	id-ConcurrentWarningMessageInd,
	id-CoreNetworkAssistanceInformationForInactive,
	id-CriticalityDiagnostics,
	id-DataCodingScheme,
	id-DefaultPagingDRX,
	id-DirectForwardingPathAvailability,
	id-DL-CP-SecurityInformation,
	id-EarlyStatusTransfer-TransparentContainer,
	id-EDT-Session,
	id-EmergencyAreaIDListForRestart,
	id-EmergencyFallbackIndicator,
	id-ENDC-SONConfigurationTransferDL,
	id-ENDC-SONConfigurationTransferUL,
	id-EndIndication,
	id-Enhanced-CoverageRestriction,
	id-EUTRA-CGI,
	id-Extended-AMFName,
	id-Extended-ConnectedTime,
	id-Extended-RANNodeName,
	id-FiveG-S-TMSI,
	id-GlobalRANNodeID,
	id-GUAMI,
	id-HandoverFlag,
	id-HandoverType,
	id-IAB-Authorized,
	id-IAB-Supported,
	id-IABNodeIndication,
	id-IMSVoiceSupportIndicator,
	id-IndexToRFSP,
	id-InfoOnRecommendedCellsAndRANNodesForPaging,
	id-IntersystemSONConfigurationTransferDL,
	id-IntersystemSONConfigurationTransferUL,
	id-LocationReportingRequestType,
	id-LTEM-Indication,
	id-LTEV2XServicesAuthorized,
	id-LTEUESidelinkAggregateMaximumBitrate,
	id-ManagementBasedMDTPLMNList,
	id-MaskedIMEISV,
	id-MessageIdentifier,
	id-MobilityRestrictionList,
	id-NAS-PDU,
	id-NASC,
	id-NASSecurityParametersFromNGRAN,
	id-NB-IoT-DefaultPagingDRX,
	id-NB-IoT-PagingDRX,
	id-NB-IoT-Paging-eDRXInfo,
	id-NB-IoT-UEPriority,
	id-NewAMF-UE-NGAP-ID,
	id-NewGUAMI,
	id-NewSecurityContextInd,
	id-NGAP-Message,
	id-NGRAN-CGI,
	id-NGRAN-TNLAssociationToRemoveList,
	id-NGRANTraceID,
	id-NotifySourceNGRANNode,
	id-NPN-AccessInformation,
	id-NR-CGI,
	id-NRPPa-PDU,
	id-NRV2XServicesAuthorized,
	id-NRUESidelinkAggregateMaximumBitrate,
	id-NumberOfBroadcastsRequested,
	id-OldAMF,
	id-OverloadStartNSSAIList,
	id-PagingAssisDataforCEcapabUE,
	id-PagingDRX,
	id-PagingeDRXInformation,
	id-PagingOrigin,
	id-PagingPriority,
	id-PDUSessionResourceAdmittedList,
	id-PDUSessionResourceFailedToModifyListModCfm,
	id-PDUSessionResourceFailedToModifyListModRes,
	id-PDUSessionResourceFailedToResumeListRESReq,
	id-PDUSessionResourceFailedToResumeListRESRes,
	id-PDUSessionResourceFailedToSetupListCxtFail,
	id-PDUSessionResourceFailedToSetupListCxtRes,
	id-PDUSessionResourceFailedToSetupListHOAck,
	id-PDUSessionResourceFailedToSetupListPSReq,
	id-PDUSessionResourceFailedToSetupListSURes,
	id-PDUSessionResourceHandoverList,
	id-PDUSessionResourceListCxtRelCpl,
	id-PDUSessionResourceListCxtRelReq,
	id-PDUSessionResourceListHORqd,
	id-PDUSessionResourceModifyListModCfm,
	id-PDUSessionResourceModifyListModInd,
	id-PDUSessionResourceModifyListModReq,
	id-PDUSessionResourceModifyListModRes,
	id-PDUSessionResourceNotifyList,
	id-PDUSessionResourceReleasedListNot,
	id-PDUSessionResourceReleasedListPSAck,
	id-PDUSessionResourceReleasedListPSFail,
	id-PDUSessionResourceReleasedListRelRes,
	id-PDUSessionResourceResumeListRESReq,
	id-PDUSessionResourceResumeListRESRes,
	id-PDUSessionResourceSecondaryRATUsageList,
	id-PDUSessionResourceSetupListCxtReq,
	id-PDUSessionResourceSetupListCxtRes,
	id-PDUSessionResourceSetupListHOReq,
	id-PDUSessionResourceSetupListSUReq,
	id-PDUSessionResourceSetupListSURes,
	id-PDUSessionResourceSuspendListSUSReq,
	id-PDUSessionResourceSwitchedList,
	id-PDUSessionResourceToBeSwitchedDLList,
	id-PDUSessionResourceToReleaseListHOCmd,
	id-PDUSessionResourceToReleaseListRelCmd,
	id-PLMNSupportList,
	id-PrivacyIndicator,
	id-PWSFailedCellIDList,
	id-PC5QoSParameters,
	id-RANNodeName,
	id-RANPagingPriority,
	id-RANStatusTransfer-TransparentContainer,
	id-RAN-UE-NGAP-ID, 
	id-RedirectionVoiceFallback,
	id-RelativeAMFCapacity,
	id-RepetitionPeriod,
	id-ResetType,
	id-RGLevelWirelineAccessCharacteristics,
	id-RoutingID,
	id-RRCEstablishmentCause,
	id-RRCInactiveTransitionReportRequest,
	id-RRC-Resume-Cause,
	id-RRCState,
	id-SecurityContext,
	id-SecurityKey,
	id-SelectedPLMNIdentity,
	id-SerialNumber,
	id-ServedGUAMIList,
	id-SliceSupportList,
	id-S-NSSAI,
	id-SONConfigurationTransferDL,
	id-SONConfigurationTransferUL,
	id-SourceAMF-UE-NGAP-ID,
	id-SourceToTarget-TransparentContainer,
	id-SourceToTarget-AMFInformationReroute,
	id-SRVCCOperationPossible,
	id-SupportedTAList,
	id-Suspend-Request-Indication,
	id-Suspend-Response-Indication,
	id-TAI,
	id-TAIListForPaging,
	id-TAIListForRestart,
	id-TargetID,
	id-TargetToSource-TransparentContainer,
	id-TargettoSource-Failure-TransparentContainer,
	id-TimeToWait,
	id-TNGFIdentityInformation,
	id-TraceActivation,
	id-TraceCollectionEntityIPAddress,
	id-TraceCollectionEntityURI,
	id-TWIFIdentityInformation,
	id-UEAggregateMaximumBitRate,
	id-UE-associatedLogicalNG-connectionList,
	id-UECapabilityInfoRequest,
	id-UEContextRequest,
	id-UE-DifferentiationInfo,
	id-UE-NGAP-IDs,
	id-UEPagingIdentity,
	id-UEPresenceInAreaOfInterestList,
	id-UERadioCapability,
	id-UERadioCapabilityForPaging,
	id-UERadioCapabilityID,
	id-UERadioCapability-EUTRA-Format,
	id-UERetentionInformation,
	id-UESecurityCapabilities,
	id-UE-UP-CIoT-Support,
	id-UL-CP-SecurityInformation,
	id-UnavailableGUAMIList,
	id-UserLocationInformation,
	id-W-AGFIdentityInformation,
	id-WarningAreaCoordinates,
	id-WarningAreaList,
	id-WarningMessageContents,
	id-WarningSecurityInfo,
	id-WarningType,
	id-WUS-Assistance-Information,
	id-RIMInformationTransfer

FROM NGAP-Constants;

-- **************************************************************
--
-- PDU SESSION MANAGEMENT ELEMENTARY PROCEDURES
--
-- **************************************************************

-- **************************************************************
--
-- PDU Session Resource Setup Elementary Procedure
--
-- **************************************************************

-- **************************************************************
--
-- PDU SESSION RESOURCE SETUP REQUEST
--
-- **************************************************************

PDUSessionResourceSetupRequest ::= SEQUENCE {
	protocolIEs		ProtocolIE-Container		{ {PDUSessionResourceSetupRequestIEs} },
	...
}

PDUSessionResourceSetupRequestIEs NGAP-PROTOCOL-IES ::= {
	{ ID id-AMF-UE-NGAP-ID							CRITICALITY reject	TYPE AMF-UE-NGAP-ID								PRESENCE mandatory	}|
	{ ID id-RAN-UE-NGAP-ID							CRITICALITY reject	TYPE RAN-UE-NGAP-ID								PRESENCE mandatory	}|
	{ ID id-RANPagingPriority						CRITICALITY ignore	TYPE RANPagingPriority							PRESENCE optional		}|
	{ ID id-NAS-PDU									CRITICALITY reject	TYPE NAS-PDU									PRESENCE optional		}|
	{ ID id-PDUSessionResourceSetupListSUReq		CRITICALITY reject	TYPE PDUSessionResourceSetupListSUReq		PRESENCE mandatory	}|
	{ ID id-UEAggregateMaximumBitRate				CRITICALITY ignore	TYPE UEAggregateMaximumBitRate				PRESENCE optional		},
	...
}

-- **************************************************************
--
-- PDU SESSION RESOURCE SETUP RESPONSE
--
-- **************************************************************

PDUSessionResourceSetupResponse ::= SEQUENCE {
	protocolIEs		ProtocolIE-Container		{ {PDUSessionResourceSetupResponseIEs} },
	...
}

PDUSessionResourceSetupResponseIEs NGAP-PROTOCOL-IES ::= {
	{ ID id-AMF-UE-NGAP-ID								CRITICALITY ignore	TYPE AMF-UE-NGAP-ID											PRESENCE mandatory	}|
	{ ID id-RAN-UE-NGAP-ID								CRITICALITY ignore	TYPE RAN-UE-NGAP-ID											PRESENCE mandatory	}|
	{ ID id-PDUSessionResourceSetupListSURes			CRITICALITY ignore	TYPE PDUSessionResourceSetupListSURes				PRESENCE optional		}|
	{ ID id-PDUSessionResourceFailedToSetupListSURes	CRITICALITY ignore	TYPE PDUSessionResourceFailedToSetupListSURes		PRESENCE optional		}|
	{ ID id-CriticalityDiagnostics						CRITICALITY ignore	TYPE CriticalityDiagnostics								PRESENCE optional		},
	...	
}


-- **************************************************************
--
-- PDU Session Resource Release Elementary Procedure
--
-- **************************************************************

-- **************************************************************
--
-- PDU SESSION RESOURCE RELEASE COMMAND
--
-- **************************************************************

PDUSessionResourceReleaseCommand ::= SEQUENCE {
	protocolIEs		ProtocolIE-Container		{ {PDUSessionResourceReleaseCommandIEs} },
	...
}

PDUSessionResourceReleaseCommandIEs NGAP-PROTOCOL-IES ::= {
	{ ID id-AMF-UE-NGAP-ID								CRITICALITY reject	TYPE AMF-UE-NGAP-ID										PRESENCE mandatory	}|
	{ ID id-RAN-UE-NGAP-ID								CRITICALITY reject	TYPE RAN-UE-NGAP-ID										PRESENCE mandatory	}|
	{ ID id-RANPagingPriority							CRITICALITY ignore	TYPE RANPagingPriority								PRESENCE optional		}|
	{ ID id-NAS-PDU										CRITICALITY ignore	TYPE NAS-PDU											PRESENCE optional		}|
	{ ID id-PDUSessionResourceToReleaseListRelCmd		CRITICALITY reject	TYPE PDUSessionResourceToReleaseListRelCmd		PRESENCE mandatory	},
	...
}

-- **************************************************************
--
-- PDU SESSION RESOURCE RELEASE RESPONSE
--
-- **************************************************************

PDUSessionResourceReleaseResponse ::= SEQUENCE {
	protocolIEs		ProtocolIE-Container		{ {PDUSessionResourceReleaseResponseIEs} },
	...
}

PDUSessionResourceReleaseResponseIEs NGAP-PROTOCOL-IES ::= {
	{ ID id-AMF-UE-NGAP-ID								CRITICALITY ignore	TYPE AMF-UE-NGAP-ID										PRESENCE mandatory	}|
	{ ID id-RAN-UE-NGAP-ID								CRITICALITY ignore	TYPE RAN-UE-NGAP-ID										PRESENCE mandatory	}|
	{ ID id-PDUSessionResourceReleasedListRelRes			CRITICALITY ignore	TYPE PDUSessionResourceReleasedListRelRes		PRESENCE mandatory	}|
	{ ID id-UserLocationInformation						CRITICALITY ignore	TYPE UserLocationInformation						PRESENCE optional		}|
	{ ID id-CriticalityDiagnostics						CRITICALITY ignore	TYPE CriticalityDiagnostics							PRESENCE optional		},
	...
}

-- **************************************************************
--
-- PDU Session Resource Modify Elementary Procedure
--
-- **************************************************************

-- **************************************************************
--
-- PDU SESSION RESOURCE MODIFY REQUEST
--
-- **************************************************************

PDUSessionResourceModifyRequest ::= SEQUENCE {
	protocolIEs		ProtocolIE-Container		{ {PDUSessionResourceModifyRequestIEs} },
	...
}

PDUSessionResourceModifyRequestIEs NGAP-PROTOCOL-IES ::= {
	{ ID id-AMF-UE-NGAP-ID							CRITICALITY reject	TYPE AMF-UE-NGAP-ID								PRESENCE mandatory	}|
	{ ID id-RAN-UE-NGAP-ID							CRITICALITY reject	TYPE RAN-UE-NGAP-ID								PRESENCE mandatory	}|
	{ ID id-RANPagingPriority						CRITICALITY ignore	TYPE RANPagingPriority							PRESENCE optional		}|
	{ ID id-PDUSessionResourceModifyListModReq		CRITICALITY reject	TYPE PDUSessionResourceModifyListModReq	PRESENCE mandatory	},
	...
}

-- **************************************************************
--
-- PDU SESSION RESOURCE MODIFY RESPONSE
--
-- **************************************************************

PDUSessionResourceModifyResponse ::= SEQUENCE {
	protocolIEs		ProtocolIE-Container		{ {PDUSessionResourceModifyResponseIEs} },
	...
}

PDUSessionResourceModifyResponseIEs NGAP-PROTOCOL-IES ::= {
	{ ID id-AMF-UE-NGAP-ID									CRITICALITY ignore	TYPE AMF-UE-NGAP-ID										PRESENCE mandatory	}|
	{ ID id-RAN-UE-NGAP-ID									CRITICALITY ignore	TYPE RAN-UE-NGAP-ID										PRESENCE mandatory	}|
	{ ID id-PDUSessionResourceModifyListModRes				CRITICALITY ignore	TYPE PDUSessionResourceModifyListModRes			PRESENCE optional		}|
	{ ID id-PDUSessionResourceFailedToModifyListModRes		CRITICALITY ignore	TYPE PDUSessionResourceFailedToModifyListModRes		PRESENCE optional	}|
	{ ID id-UserLocationInformation							CRITICALITY ignore	TYPE UserLocationInformation							PRESENCE optional		}|
	{ ID id-CriticalityDiagnostics							CRITICALITY ignore	TYPE CriticalityDiagnostics							PRESENCE optional		},
	...
}


-- **************************************************************
--
-- PDU Session Resource Notify Elementary Procedure
--
-- **************************************************************

-- **************************************************************
--
-- PDU SESSION RESOURCE NOTIFY
--
-- **************************************************************

PDUSessionResourceNotify ::= SEQUENCE {
	protocolIEs		ProtocolIE-Container		{ {PDUSessionResourceNotifyIEs} },
	...
}

PDUSessionResourceNotifyIEs NGAP-PROTOCOL-IES ::= {
	{ ID id-AMF-UE-NGAP-ID							CRITICALITY reject	TYPE AMF-UE-NGAP-ID									PRESENCE mandatory	}|
	{ ID id-RAN-UE-NGAP-ID							CRITICALITY reject	TYPE RAN-UE-NGAP-ID									PRESENCE mandatory	}|
	{ ID id-PDUSessionResourceNotifyList			CRITICALITY reject	TYPE PDUSessionResourceNotifyList				PRESENCE optional		}|
	{ ID id-PDUSessionResourceReleasedListNot		CRITICALITY ignore	TYPE PDUSessionResourceReleasedListNot		PRESENCE optional		}|
	{ ID id-UserLocationInformation					CRITICALITY ignore	TYPE UserLocationInformation						PRESENCE optional		},
	...
}


-- **************************************************************
--
-- PDU Session Resource Modify Indication Elementary Procedure
--
-- **************************************************************

-- **************************************************************
--
-- PDU SESSION RESOURCE MODIFY INDICATION
--
-- **************************************************************

PDUSessionResourceModifyIndication ::= SEQUENCE {
	protocolIEs		ProtocolIE-Container		{ {PDUSessionResourceModifyIndicationIEs} },
	...
}

PDUSessionResourceModifyIndicationIEs NGAP-PROTOCOL-IES ::= {
	{ ID id-AMF-UE-NGAP-ID							CRITICALITY reject	TYPE AMF-UE-NGAP-ID									PRESENCE mandatory	}|
	{ ID id-RAN-UE-NGAP-ID							CRITICALITY reject	TYPE RAN-UE-NGAP-ID									PRESENCE mandatory	}|
	{ ID id-PDUSessionResourceModifyListModInd		CRITICALITY reject	TYPE PDUSessionResourceModifyListModInd		PRESENCE mandatory	}|
	{ ID id-UserLocationInformation					CRITICALITY ignore	TYPE UserLocationInformation						PRESENCE optional		},
	...
}

-- **************************************************************
--
-- PDU SESSION RESOURCE MODIFY CONFIRM
--
-- **************************************************************

PDUSessionResourceModifyConfirm ::= SEQUENCE {
	protocolIEs		ProtocolIE-Container		{ {PDUSessionResourceModifyConfirmIEs} },
	...
}

PDUSessionResourceModifyConfirmIEs NGAP-PROTOCOL-IES ::= {
	{ ID id-AMF-UE-NGAP-ID								CRITICALITY ignore	TYPE AMF-UE-NGAP-ID									PRESENCE mandatory	}|
	{ ID id-RAN-UE-NGAP-ID								CRITICALITY ignore	TYPE RAN-UE-NGAP-ID									PRESENCE mandatory	}|
	{ ID id-PDUSessionResourceModifyListModCfm			CRITICALITY ignore	TYPE PDUSessionResourceModifyListModCfm		PRESENCE optional	}|
	{ ID id-PDUSessionResourceFailedToModifyListModCfm	CRITICALITY ignore	TYPE PDUSessionResourceFailedToModifyListModCfm		PRESENCE optional	}|
	{ ID id-CriticalityDiagnostics						CRITICALITY ignore	TYPE CriticalityDiagnostics						PRESENCE optional		},
	...
}

-- **************************************************************
--
-- UE CONTEXT MANAGEMENT ELEMENTARY PROCEDURES
--
-- **************************************************************

-- **************************************************************
--
-- Initial Context Setup Elementary Procedure
--
-- **************************************************************

-- **************************************************************
--
-- INITIAL CONTEXT SETUP REQUEST
--
-- **************************************************************

InitialContextSetupRequest ::= SEQUENCE {
	protocolIEs		ProtocolIE-Container		{ {InitialContextSetupRequestIEs} },
	...
}

InitialContextSetupRequestIEs NGAP-PROTOCOL-IES ::= {
	{ ID id-AMF-UE-NGAP-ID							CRITICALITY reject	TYPE AMF-UE-NGAP-ID										PRESENCE mandatory	}|
	{ ID id-RAN-UE-NGAP-ID							CRITICALITY reject	TYPE RAN-UE-NGAP-ID										PRESENCE mandatory	}|
	{ ID id-OldAMF									CRITICALITY reject	TYPE AMFName											PRESENCE optional		}|
	{ ID id-UEAggregateMaximumBitRate				CRITICALITY reject	TYPE UEAggregateMaximumBitRate						PRESENCE conditional	}|
	{ ID id-CoreNetworkAssistanceInformationForInactive		CRITICALITY ignore	TYPE CoreNetworkAssistanceInformationForInactive		PRESENCE optional		}|
	{ ID id-GUAMI									CRITICALITY reject	TYPE GUAMI												PRESENCE mandatory	}|
	{ ID id-PDUSessionResourceSetupListCxtReq		CRITICALITY reject	TYPE PDUSessionResourceSetupListCxtReq			PRESENCE optional		}|
	{ ID id-AllowedNSSAI							CRITICALITY reject	TYPE AllowedNSSAI										PRESENCE mandatory	}|
	{ ID id-UESecurityCapabilities					CRITICALITY reject	TYPE UESecurityCapabilities							PRESENCE mandatory	}|
	{ ID id-SecurityKey								CRITICALITY reject	TYPE SecurityKey										PRESENCE mandatory	}|
	{ ID id-TraceActivation							CRITICALITY ignore	TYPE TraceActivation									PRESENCE optional		}|
	{ ID id-MobilityRestrictionList					CRITICALITY ignore	TYPE MobilityRestrictionList							PRESENCE optional		}|
	{ ID id-UERadioCapability						CRITICALITY ignore	TYPE UERadioCapability									PRESENCE optional		}|
	{ ID id-IndexToRFSP								CRITICALITY ignore	TYPE IndexToRFSP										PRESENCE optional		}|
	{ ID id-MaskedIMEISV							CRITICALITY ignore	TYPE MaskedIMEISV										PRESENCE optional		}|
	{ ID id-NAS-PDU									CRITICALITY ignore	TYPE NAS-PDU											PRESENCE optional		}|
	{ ID id-EmergencyFallbackIndicator				CRITICALITY reject	TYPE EmergencyFallbackIndicator						PRESENCE optional		}|
	{ ID id-RRCInactiveTransitionReportRequest		CRITICALITY ignore	TYPE RRCInactiveTransitionReportRequest			PRESENCE optional		}|
	{ ID id-UERadioCapabilityForPaging				CRITICALITY ignore	TYPE UERadioCapabilityForPaging						PRESENCE optional		}|
	{ ID id-RedirectionVoiceFallback				CRITICALITY ignore	TYPE RedirectionVoiceFallback						PRESENCE optional		}|
	{ ID id-LocationReportingRequestType			CRITICALITY ignore	TYPE LocationReportingRequestType					PRESENCE optional		}|
	{ ID id-CNAssistedRANTuning						CRITICALITY ignore	TYPE CNAssistedRANTuning								PRESENCE optional		}|
	{ ID id-SRVCCOperationPossible					CRITICALITY ignore	TYPE SRVCCOperationPossible							PRESENCE optional		}|
	{ ID id-IAB-Authorized							CRITICALITY ignore	TYPE IAB-Authorized										PRESENCE optional		}|
	{ ID id-Enhanced-CoverageRestriction			CRITICALITY ignore	TYPE Enhanced-CoverageRestriction					PRESENCE optional		}|
	{ ID id-Extended-ConnectedTime					CRITICALITY ignore	TYPE Extended-ConnectedTime							PRESENCE optional		}|
	{ ID id-UE-DifferentiationInfo					CRITICALITY ignore	TYPE UE-DifferentiationInfo							PRESENCE optional		}|
{ ID id-NRV2XServicesAuthorized					CRITICALITY ignore	TYPE NRV2XServicesAuthorized							PRESENCE optional		}|
{ ID id-LTEV2XServicesAuthorized				CRITICALITY ignore	TYPE LTEV2XServicesAuthorized						PRESENCE optional		}|
{ ID id-NRUESidelinkAggregateMaximumBitrate		CRITICALITY ignore	TYPE NRUESidelinkAggregateMaximumBitrate			PRESENCE optional		}|
{ ID id-LTEUESidelinkAggregateMaximumBitrate	CRITICALITY ignore	TYPE LTEUESidelinkAggregateMaximumBitrate		PRESENCE optional		}|
	{ ID id-PC5QoSParameters						CRITICALITY ignore	TYPE PC5QoSParameters									PRESENCE optional 	}|
	{ ID id-CEmodeBrestricted						CRITICALITY ignore	TYPE CEmodeBrestricted									PRESENCE optional		}|
	{ ID id-UE-UP-CIoT-Support						CRITICALITY ignore	TYPE UE-UP-CIoT-Support									PRESENCE optional		}|
	{ ID id-RGLevelWirelineAccessCharacteristics	CRITICALITY ignore	TYPE RGLevelWirelineAccessCharacteristics		PRESENCE optional		}|
	{ ID id-ManagementBasedMDTPLMNList				CRITICALITY ignore	TYPE MDTPLMNList										PRESENCE optional		}|
	{ ID id-UERadioCapabilityID						CRITICALITY reject	TYPE UERadioCapabilityID								PRESENCE optional		},
	...
}

-- **************************************************************
--
-- INITIAL CONTEXT SETUP RESPONSE
--
-- **************************************************************

InitialContextSetupResponse ::= SEQUENCE {
	protocolIEs		ProtocolIE-Container		{ {InitialContextSetupResponseIEs} },
	...
}

InitialContextSetupResponseIEs NGAP-PROTOCOL-IES ::= {
	{ ID id-AMF-UE-NGAP-ID								CRITICALITY ignore	TYPE AMF-UE-NGAP-ID												PRESENCE mandatory	}|
	{ ID id-RAN-UE-NGAP-ID								CRITICALITY ignore	TYPE RAN-UE-NGAP-ID												PRESENCE mandatory	}|
	{ ID id-PDUSessionResourceSetupListCxtRes			CRITICALITY ignore	TYPE PDUSessionResourceSetupListCxtRes					PRESENCE optional		}|
	{ ID id-PDUSessionResourceFailedToSetupListCxtRes	CRITICALITY ignore	TYPE PDUSessionResourceFailedToSetupListCxtRes		PRESENCE optional		}|
	{ ID id-CriticalityDiagnostics						CRITICALITY ignore	TYPE CriticalityDiagnostics									PRESENCE optional		},
	...
}


-- **************************************************************
--
-- INITIAL CONTEXT SETUP FAILURE
--
-- **************************************************************

InitialContextSetupFailure ::= SEQUENCE {
	protocolIEs		ProtocolIE-Container		{ {InitialContextSetupFailureIEs} },
	...
}

InitialContextSetupFailureIEs NGAP-PROTOCOL-IES ::= {
	{ ID id-AMF-UE-NGAP-ID								CRITICALITY ignore	TYPE AMF-UE-NGAP-ID												PRESENCE mandatory	}|
	{ ID id-RAN-UE-NGAP-ID								CRITICALITY ignore	TYPE RAN-UE-NGAP-ID												PRESENCE mandatory	}|
	{ ID id-PDUSessionResourceFailedToSetupListCxtFail	CRITICALITY ignore	TYPE PDUSessionResourceFailedToSetupListCxtFail		PRESENCE optional		}|
	{ ID id-Cause										CRITICALITY ignore	TYPE Cause														PRESENCE mandatory	}|
	{ ID id-CriticalityDiagnostics						CRITICALITY ignore	TYPE CriticalityDiagnostics									PRESENCE optional		},
	...
}

-- **************************************************************
--
-- UE Context Release Request Elementary Procedure
--
-- **************************************************************

-- **************************************************************
--
-- UE CONTEXT RELEASE REQUEST
--
-- **************************************************************

UEContextReleaseRequest ::= SEQUENCE {
	protocolIEs		ProtocolIE-Container		{ {UEContextReleaseRequest-IEs} },
	...
}

UEContextReleaseRequest-IEs NGAP-PROTOCOL-IES ::= {
	{ ID id-AMF-UE-NGAP-ID						CRITICALITY reject	TYPE AMF-UE-NGAP-ID								PRESENCE mandatory	}|
	{ ID id-RAN-UE-NGAP-ID						CRITICALITY reject	TYPE RAN-UE-NGAP-ID								PRESENCE mandatory	}|
	{ ID id-PDUSessionResourceListCxtRelReq		CRITICALITY reject	TYPE PDUSessionResourceListCxtRelReq		PRESENCE optional		}|
	{ ID id-Cause								CRITICALITY ignore	TYPE Cause										PRESENCE mandatory	},
	...
}

-- **************************************************************
--
-- UE Context Release Elementary Procedure
--
-- **************************************************************

-- **************************************************************
--
-- UE CONTEXT RELEASE COMMAND
--
-- **************************************************************

UEContextReleaseCommand ::= SEQUENCE {
	protocolIEs		ProtocolIE-Container		{ {UEContextReleaseCommand-IEs} },
	...
}

UEContextReleaseCommand-IEs NGAP-PROTOCOL-IES ::= {
	{ ID id-UE-NGAP-IDs				CRITICALITY reject	TYPE UE-NGAP-IDs			PRESENCE mandatory	}|
	{ ID id-Cause					CRITICALITY ignore	TYPE Cause					PRESENCE mandatory	},
	...
}

-- **************************************************************
--
-- UE CONTEXT RELEASE COMPLETE
--
-- **************************************************************

UEContextReleaseComplete ::= SEQUENCE {
	protocolIEs		ProtocolIE-Container		{ {UEContextReleaseComplete-IEs} },
	...
}

UEContextReleaseComplete-IEs NGAP-PROTOCOL-IES ::= {
	{ ID id-AMF-UE-NGAP-ID								CRITICALITY ignore	TYPE AMF-UE-NGAP-ID											PRESENCE mandatory	}|
	{ ID id-RAN-UE-NGAP-ID								CRITICALITY ignore	TYPE RAN-UE-NGAP-ID											PRESENCE mandatory	}|
	{ ID id-UserLocationInformation						CRITICALITY ignore	TYPE UserLocationInformation							PRESENCE optional		}|
	{ ID id-InfoOnRecommendedCellsAndRANNodesForPaging	CRITICALITY ignore	TYPE InfoOnRecommendedCellsAndRANNodesForPaging	PRESENCE optional		}|
	{ ID id-PDUSessionResourceListCxtRelCpl				CRITICALITY	reject	TYPE PDUSessionResourceListCxtRelCpl					PRESENCE optional		}|
	{ ID id-CriticalityDiagnostics						CRITICALITY ignore	TYPE CriticalityDiagnostics								PRESENCE optional		}|
	{ ID id-PagingAssisDataforCEcapabUE					CRITICALITY ignore	TYPE PagingAssisDataforCEcapabUE						PRESENCE optional		},
	...
}

-- **************************************************************
--
-- UE Context Resume Elementary Procedure
--
-- **************************************************************

-- **************************************************************
--
-- UE CONTEXT RESUME REQUEST
--
-- **************************************************************

UEContextResumeRequest ::= SEQUENCE {
	protocolIEs		ProtocolIE-Container		{ {UEContextResumeRequestIEs} },
	...
}

UEContextResumeRequestIEs NGAP-PROTOCOL-IES ::= {
	{ ID id-AMF-UE-NGAP-ID							CRITICALITY reject	TYPE AMF-UE-NGAP-ID										PRESENCE mandatory	}|
	{ ID id-RAN-UE-NGAP-ID							CRITICALITY reject	TYPE RAN-UE-NGAP-ID										PRESENCE mandatory	}|
	{ ID id-RRC-Resume-Cause						CRITICALITY ignore	TYPE RRCEstablishmentCause							PRESENCE mandatory	}|
	{ ID id-PDUSessionResourceResumeListRESReq		CRITICALITY reject	TYPE PDUSessionResourceResumeListRESReq			PRESENCE optional		}|
	{ ID id-PDUSessionResourceFailedToResumeListRESReq		CRITICALITY reject	TYPE PDUSessionResourceFailedToResumeListRESReq			PRESENCE optional		}|
	{ ID id-Suspend-Request-Indication				CRITICALITY ignore	TYPE Suspend-Request-Indication						PRESENCE optional		}|
	{ ID id-InfoOnRecommendedCellsAndRANNodesForPaging	CRITICALITY ignore	TYPE InfoOnRecommendedCellsAndRANNodesForPaging		PRESENCE optional		}|
	{ ID id-PagingAssisDataforCEcapabUE					CRITICALITY ignore	TYPE PagingAssisDataforCEcapabUE							PRESENCE optional		},
	...
}

-- **************************************************************
--
-- UE CONTEXT RESUME RESPONSE
--
-- **************************************************************

UEContextResumeResponse ::= SEQUENCE {
	protocolIEs		ProtocolIE-Container		{ {UEContextResumeResponseIEs} },
	...
}

UEContextResumeResponseIEs NGAP-PROTOCOL-IES ::= {
	{ ID id-AMF-UE-NGAP-ID							CRITICALITY ignore	TYPE AMF-UE-NGAP-ID										PRESENCE mandatory	}|
	{ ID id-RAN-UE-NGAP-ID							CRITICALITY ignore	TYPE RAN-UE-NGAP-ID										PRESENCE mandatory	}|
	{ ID id-PDUSessionResourceResumeListRESRes		CRITICALITY reject	TYPE PDUSessionResourceResumeListRESRes			PRESENCE optional		}|
	{ ID id-PDUSessionResourceFailedToResumeListRESRes		CRITICALITY reject	TYPE PDUSessionResourceFailedToResumeListRESRes			PRESENCE optional		}|
	{ ID id-SecurityContext							CRITICALITY reject	TYPE SecurityContext									PRESENCE optional		}|
	{ ID id-Suspend-Response-Indication				CRITICALITY ignore	TYPE Suspend-Response-Indication					PRESENCE optional		}|
	{ ID id-Extended-ConnectedTime					CRITICALITY ignore	TYPE Extended-ConnectedTime							PRESENCE optional		}|
	{ ID id-CriticalityDiagnostics					CRITICALITY ignore	TYPE CriticalityDiagnostics							PRESENCE optional		},
	...
}

-- **************************************************************
--
-- UE CONTEXT RESUME FAILURE
--
-- **************************************************************

UEContextResumeFailure ::= SEQUENCE {
	protocolIEs		ProtocolIE-Container		{ { UEContextResumeFailureIEs} },
	...
}

UEContextResumeFailureIEs NGAP-PROTOCOL-IES ::= {	
	{ ID id-AMF-UE-NGAP-ID				CRITICALITY ignore	TYPE AMF-UE-NGAP-ID				PRESENCE mandatory	}|
	{ ID id-RAN-UE-NGAP-ID				CRITICALITY ignore	TYPE RAN-UE-NGAP-ID				PRESENCE mandatory	}|
	{ ID id-Cause						CRITICALITY ignore	TYPE Cause						PRESENCE mandatory	}|
	{ ID id-CriticalityDiagnostics		CRITICALITY ignore	TYPE CriticalityDiagnostics		PRESENCE optional		},
	...
}


-- **************************************************************
--
-- UE Context Suspend Elementary Procedure
--
-- **************************************************************

-- **************************************************************
--
-- UE CONTEXT SUSPEND REQUEST
--
-- **************************************************************

UEContextSuspendRequest ::= SEQUENCE {
	protocolIEs		ProtocolIE-Container		{ {UEContextSuspendRequestIEs} },
	...
}

UEContextSuspendRequestIEs NGAP-PROTOCOL-IES ::= {
	{ ID id-AMF-UE-NGAP-ID								CRITICALITY reject	TYPE AMF-UE-NGAP-ID												PRESENCE mandatory	}|
	{ ID id-RAN-UE-NGAP-ID								CRITICALITY reject	TYPE RAN-UE-NGAP-ID												PRESENCE mandatory	}|
	{ ID id-InfoOnRecommendedCellsAndRANNodesForPaging	CRITICALITY ignore	TYPE InfoOnRecommendedCellsAndRANNodesForPaging		PRESENCE optional		}|
	{ ID id-PagingAssisDataforCEcapabUE					CRITICALITY ignore	TYPE PagingAssisDataforCEcapabUE							PRESENCE optional		}|
	{ ID id-PDUSessionResourceSuspendListSUSReq			CRITICALITY reject	TYPE PDUSessionResourceSuspendListSUSReq				PRESENCE optional		},	...
}

-- **************************************************************
--
-- UE CONTEXT SUSPEND RESPONSE
--
-- **************************************************************

UEContextSuspendResponse ::= SEQUENCE {
	protocolIEs		ProtocolIE-Container		{ {UEContextSuspendResponseIEs} },
	...
}

UEContextSuspendResponseIEs NGAP-PROTOCOL-IES ::= {
	{ ID id-AMF-UE-NGAP-ID							CRITICALITY ignore	TYPE AMF-UE-NGAP-ID										PRESENCE mandatory	}|
	{ ID id-RAN-UE-NGAP-ID							CRITICALITY ignore	TYPE RAN-UE-NGAP-ID										PRESENCE mandatory	}|
	{ ID id-SecurityContext							CRITICALITY reject	TYPE SecurityContext									PRESENCE optional		}|
	{ ID id-CriticalityDiagnostics					CRITICALITY ignore	TYPE CriticalityDiagnostics							PRESENCE optional		},
	...
}

-- **************************************************************
--
-- UE CONTEXT SUSPEND FAILURE
--
-- **************************************************************

UEContextSuspendFailure ::= SEQUENCE {
	protocolIEs		ProtocolIE-Container		{ { UEContextSuspendFailureIEs} },
	...
}

UEContextSuspendFailureIEs NGAP-PROTOCOL-IES ::= {	
	{ ID id-AMF-UE-NGAP-ID				CRITICALITY ignore	TYPE AMF-UE-NGAP-ID				PRESENCE mandatory	}|
	{ ID id-RAN-UE-NGAP-ID				CRITICALITY ignore	TYPE RAN-UE-NGAP-ID				PRESENCE mandatory	}|
	{ ID id-Cause						CRITICALITY ignore	TYPE Cause						PRESENCE mandatory	}|
	{ ID id-CriticalityDiagnostics		CRITICALITY ignore	TYPE CriticalityDiagnostics		PRESENCE optional		},
	...
}

-- **************************************************************
--
-- UE Context Modification Elementary Procedure
--
-- **************************************************************

-- **************************************************************
--
-- UE CONTEXT MODIFICATION REQUEST
--
-- **************************************************************

UEContextModificationRequest ::= SEQUENCE {
	protocolIEs		ProtocolIE-Container		{ {UEContextModificationRequestIEs} },
	...
}

UEContextModificationRequestIEs NGAP-PROTOCOL-IES ::= {
	{ ID id-AMF-UE-NGAP-ID							CRITICALITY reject	TYPE AMF-UE-NGAP-ID									PRESENCE mandatory	}|
	{ ID id-RAN-UE-NGAP-ID							CRITICALITY reject	TYPE RAN-UE-NGAP-ID									PRESENCE mandatory	}|
	{ ID id-RANPagingPriority						CRITICALITY ignore	TYPE RANPagingPriority								PRESENCE optional		}|
	{ ID id-SecurityKey								CRITICALITY reject	TYPE SecurityKey									PRESENCE optional		}|
	{ ID id-IndexToRFSP								CRITICALITY ignore	TYPE IndexToRFSP									PRESENCE optional		}|
	{ ID id-UEAggregateMaximumBitRate				CRITICALITY ignore	TYPE UEAggregateMaximumBitRate					PRESENCE optional		}|
	{ ID id-UESecurityCapabilities					CRITICALITY reject	TYPE UESecurityCapabilities						PRESENCE optional		}|
	{ ID id-CoreNetworkAssistanceInformationForInactive		CRITICALITY ignore	TYPE CoreNetworkAssistanceInformationForInactive		PRESENCE optional		}|
	{ ID id-EmergencyFallbackIndicator				CRITICALITY reject	TYPE EmergencyFallbackIndicator					PRESENCE optional		}|
	{ ID id-NewAMF-UE-NGAP-ID						CRITICALITY reject	TYPE AMF-UE-NGAP-ID									PRESENCE optional		}|
	{ ID id-RRCInactiveTransitionReportRequest		CRITICALITY ignore	TYPE RRCInactiveTransitionReportRequest		PRESENCE optional		}|
	{ ID id-NewGUAMI								CRITICALITY reject	TYPE GUAMI											PRESENCE optional		}|
	{ ID id-CNAssistedRANTuning						CRITICALITY ignore	TYPE CNAssistedRANTuning							PRESENCE optional		}|
	{ ID id-SRVCCOperationPossible					CRITICALITY ignore	TYPE SRVCCOperationPossible						PRESENCE optional		}|
	{ ID id-IAB-Authorized							CRITICALITY ignore	TYPE IAB-Authorized									PRESENCE optional		}|
	{ ID id-NRV2XServicesAuthorized					CRITICALITY ignore	TYPE NRV2XServicesAuthorized						PRESENCE optional		}|
	{ ID id-LTEV2XServicesAuthorized				CRITICALITY ignore	TYPE LTEV2XServicesAuthorized					PRESENCE optional		}|
	{ ID id-NRUESidelinkAggregateMaximumBitrate		CRITICALITY ignore	TYPE NRUESidelinkAggregateMaximumBitrate		PRESENCE optional		}|
	{ ID id-LTEUESidelinkAggregateMaximumBitrate	CRITICALITY ignore	TYPE LTEUESidelinkAggregateMaximumBitrate	PRESENCE optional		}|
	{ ID id-PC5QoSParameters						CRITICALITY ignore	TYPE PC5QoSParameters								PRESENCE optional 	}|
	{ ID id-UERadioCapabilityID						CRITICALITY reject	TYPE UERadioCapabilityID							PRESENCE optional		}|
	{ ID id-RGLevelWirelineAccessCharacteristics	CRITICALITY ignore	TYPE RGLevelWirelineAccessCharacteristics	PRESENCE optional		},
	...
}

-- **************************************************************
--
-- UE CONTEXT MODIFICATION RESPONSE
--
-- **************************************************************

UEContextModificationResponse ::= SEQUENCE {
	protocolIEs		ProtocolIE-Container		{ {UEContextModificationResponseIEs} },
	...
}

UEContextModificationResponseIEs NGAP-PROTOCOL-IES ::= {	
	{ ID id-AMF-UE-NGAP-ID				CRITICALITY ignore	TYPE AMF-UE-NGAP-ID				PRESENCE mandatory	}|
	{ ID id-RAN-UE-NGAP-ID				CRITICALITY ignore	TYPE RAN-UE-NGAP-ID				PRESENCE mandatory	}|
	{ ID id-RRCState					CRITICALITY ignore	TYPE RRCState					PRESENCE optional		}|
	{ ID id-UserLocationInformation		CRITICALITY ignore	TYPE UserLocationInformation	PRESENCE optional 	}|
	{ ID id-CriticalityDiagnostics		CRITICALITY ignore	TYPE CriticalityDiagnostics		PRESENCE optional		},
	...
}

-- **************************************************************
--
-- UE CONTEXT MODIFICATION FAILURE
--
-- **************************************************************

UEContextModificationFailure ::= SEQUENCE {
	protocolIEs		ProtocolIE-Container		{ {UEContextModificationFailureIEs} },
	...
}

UEContextModificationFailureIEs NGAP-PROTOCOL-IES ::= {	
	{ ID id-AMF-UE-NGAP-ID				CRITICALITY ignore	TYPE AMF-UE-NGAP-ID				PRESENCE mandatory	}|
	{ ID id-RAN-UE-NGAP-ID				CRITICALITY ignore	TYPE RAN-UE-NGAP-ID				PRESENCE mandatory	}|
	{ ID id-Cause						CRITICALITY ignore	TYPE Cause						PRESENCE mandatory	}|
	{ ID id-CriticalityDiagnostics		CRITICALITY ignore	TYPE CriticalityDiagnostics		PRESENCE optional		},
	...
}

-- **************************************************************
--
-- RRC INACTIVE TRANSITION REPORT
--
-- **************************************************************

RRCInactiveTransitionReport ::= SEQUENCE {
	protocolIEs		ProtocolIE-Container		{ {RRCInactiveTransitionReportIEs} },
	...
}

RRCInactiveTransitionReportIEs NGAP-PROTOCOL-IES ::= {
	{ ID id-AMF-UE-NGAP-ID				CRITICALITY reject	TYPE AMF-UE-NGAP-ID					PRESENCE mandatory	}|
	{ ID id-RAN-UE-NGAP-ID				CRITICALITY reject	TYPE RAN-UE-NGAP-ID					PRESENCE mandatory	}|
	{ ID id-RRCState					CRITICALITY ignore	TYPE RRCState						PRESENCE mandatory	}|
	{ ID id-UserLocationInformation		CRITICALITY ignore	TYPE UserLocationInformation		PRESENCE mandatory	},
	...
}

-- **************************************************************
--
-- Retrieve UE Information 
--
-- **************************************************************

RetrieveUEInformation ::= SEQUENCE {
	protocolIEs			ProtocolIE-Container       { { RetrieveUEInformationIEs} },
	...
}

RetrieveUEInformationIEs NGAP-PROTOCOL-IES ::= {
		{ ID id-FiveG-S-TMSI					CRITICALITY reject	TYPE FiveG-S-TMSI				PRESENCE mandatory	},
	...

}

-- **************************************************************

-- UE Information Transfer
--
-- **************************************************************

UEInformationTransfer ::= SEQUENCE {
	protocolIEs			ProtocolIE-Container       { {  UEInformationTransferIEs} },
	...
}

UEInformationTransferIEs NGAP-PROTOCOL-IES ::= {
	{ ID id-FiveG-S-TMSI				CRITICALITY reject 	TYPE FiveG-S-TMSI				PRESENCE mandatory	}|
	{ ID id-NB-IoT-UEPriority			CRITICALITY ignore	TYPE NB-IoT-UEPriority			PRESENCE optional		}|
	{ ID id-UERadioCapability			CRITICALITY ignore	TYPE UERadioCapability			PRESENCE optional		}|
	{ ID id-S-NSSAI						CRITICALITY ignore	TYPE S-NSSAI					PRESENCE optional		}|
	{ ID id-AllowedNSSAI				CRITICALITY ignore	TYPE AllowedNSSAI				PRESENCE optional		}|
	{ ID id-UE-DifferentiationInfo		CRITICALITY ignore	TYPE UE-DifferentiationInfo		PRESENCE optional		},
	...
}

-- **************************************************************
--
-- RAN CP Relocation Indication
--
-- **************************************************************

RANCPRelocationIndication ::= SEQUENCE {
	protocolIEs			ProtocolIE-Container { { RANCPRelocationIndicationIEs} },
	...
}

RANCPRelocationIndicationIEs NGAP-PROTOCOL-IES ::= {
	{ ID id-RAN-UE-NGAP-ID					CRITICALITY reject	TYPE RAN-UE-NGAP-ID					PRESENCE mandatory	}|
	{ ID id-FiveG-S-TMSI					CRITICALITY reject	TYPE FiveG-S-TMSI					PRESENCE mandatory	}|
	{ ID id-EUTRA-CGI						CRITICALITY ignore	TYPE EUTRA-CGI						PRESENCE mandatory	}|
	{ ID id-TAI								CRITICALITY ignore	TYPE TAI							PRESENCE mandatory	}|
	{ ID id-UL-CP-SecurityInformation		CRITICALITY reject	TYPE UL-CP-SecurityInformation		PRESENCE mandatory	},
	...
}

-- **************************************************************
--
-- UE MOBILITY MANAGEMENT ELEMENTARY PROCEDURES
--
-- **************************************************************

-- **************************************************************
--
-- Handover Preparation Elementary Procedure
--
-- **************************************************************

-- **************************************************************
--
-- HANDOVER REQUIRED
--
-- **************************************************************

HandoverRequired ::= SEQUENCE {
	protocolIEs		ProtocolIE-Container		{ {HandoverRequiredIEs} },
	...
}

HandoverRequiredIEs NGAP-PROTOCOL-IES ::= {	
	{ ID id-AMF-UE-NGAP-ID							CRITICALITY reject	TYPE AMF-UE-NGAP-ID									PRESENCE mandatory	}|
	{ ID id-RAN-UE-NGAP-ID							CRITICALITY reject	TYPE RAN-UE-NGAP-ID									PRESENCE mandatory	}|
	{ ID id-HandoverType							CRITICALITY reject	TYPE HandoverType									PRESENCE mandatory	}|
	{ ID id-Cause									CRITICALITY ignore	TYPE Cause											PRESENCE mandatory	}|
	{ ID id-TargetID								CRITICALITY reject	TYPE TargetID										PRESENCE mandatory	}|
	{ ID id-DirectForwardingPathAvailability		CRITICALITY ignore	TYPE DirectForwardingPathAvailability			PRESENCE optional		}|
	{ ID id-PDUSessionResourceListHORqd				CRITICALITY reject	TYPE PDUSessionResourceListHORqd				PRESENCE mandatory	}|
	{ ID id-SourceToTarget-TransparentContainer		CRITICALITY reject	TYPE SourceToTarget-TransparentContainer		PRESENCE mandatory	},
	...
}

-- **************************************************************
--
-- HANDOVER COMMAND
--
-- **************************************************************

HandoverCommand ::= SEQUENCE {
	protocolIEs		ProtocolIE-Container		{ {HandoverCommandIEs} },
	...
}

HandoverCommandIEs NGAP-PROTOCOL-IES ::= {	
	{ ID id-AMF-UE-NGAP-ID								CRITICALITY reject	TYPE AMF-UE-NGAP-ID											PRESENCE mandatory	}|
	{ ID id-RAN-UE-NGAP-ID								CRITICALITY reject	TYPE RAN-UE-NGAP-ID											PRESENCE mandatory	}|
	{ ID id-HandoverType								CRITICALITY reject	TYPE HandoverType											PRESENCE mandatory	}|
	{ ID id-NASSecurityParametersFromNGRAN				CRITICALITY reject	TYPE NASSecurityParametersFromNGRAN					PRESENCE conditional	}|
	-- This IE shall be present if HandoverType IE is set to value "5GStoEPPS" or 5GStoUTRAN --
	{ ID id-PDUSessionResourceHandoverList				CRITICALITY ignore	TYPE PDUSessionResourceHandoverList					PRESENCE optional		}|
	{ ID id-PDUSessionResourceToReleaseListHOCmd		CRITICALITY ignore	TYPE PDUSessionResourceToReleaseListHOCmd			PRESENCE optional		}|
	{ ID id-TargetToSource-TransparentContainer			CRITICALITY reject	TYPE TargetToSource-TransparentContainer			PRESENCE mandatory	}|
	{ ID id-CriticalityDiagnostics						CRITICALITY ignore	TYPE CriticalityDiagnostics								PRESENCE optional		},
	...
}


-- **************************************************************
--
-- HANDOVER PREPARATION FAILURE
--
-- **************************************************************

HandoverPreparationFailure ::= SEQUENCE {
	protocolIEs		ProtocolIE-Container		{ {HandoverPreparationFailureIEs} },
	...
}

HandoverPreparationFailureIEs NGAP-PROTOCOL-IES ::= {	
	{ ID id-AMF-UE-NGAP-ID				CRITICALITY ignore	TYPE AMF-UE-NGAP-ID				PRESENCE mandatory	}|
	{ ID id-RAN-UE-NGAP-ID				CRITICALITY ignore	TYPE RAN-UE-NGAP-ID				PRESENCE mandatory	}|
	{ ID id-Cause						CRITICALITY ignore	TYPE Cause						PRESENCE mandatory	}|
	{ ID id-CriticalityDiagnostics		CRITICALITY ignore	TYPE CriticalityDiagnostics		PRESENCE optional		}|
	{ ID id-TargettoSource-Failure-TransparentContainer		CRITICALITY ignore	TYPE TargettoSource-Failure-TransparentContainer		PRESENCE optional		},
	...
}

-- **************************************************************
--
-- Handover Resource Allocation Elementary Procedure
--
-- **************************************************************

-- **************************************************************
--
-- HANDOVER REQUEST
--
-- **************************************************************

HandoverRequest ::= SEQUENCE {
	protocolIEs		ProtocolIE-Container		{ {HandoverRequestIEs} },
	...
}

HandoverRequestIEs NGAP-PROTOCOL-IES ::= {
	{ ID id-AMF-UE-NGAP-ID							CRITICALITY reject	TYPE AMF-UE-NGAP-ID									PRESENCE mandatory	}|
	{ ID id-HandoverType							CRITICALITY reject	TYPE HandoverType									PRESENCE mandatory	}|
	{ ID id-Cause									CRITICALITY ignore	TYPE Cause											PRESENCE mandatory	}|
	{ ID id-UEAggregateMaximumBitRate				CRITICALITY reject	TYPE UEAggregateMaximumBitRate					PRESENCE mandatory	}|
	{ ID id-CoreNetworkAssistanceInformationForInactive		CRITICALITY ignore	TYPE CoreNetworkAssistanceInformationForInactive		PRESENCE optional		}|
	{ ID id-UESecurityCapabilities					CRITICALITY reject	TYPE UESecurityCapabilities						PRESENCE mandatory	}|
	{ ID id-SecurityContext							CRITICALITY reject	TYPE SecurityContext								PRESENCE mandatory	}|
	{ ID id-NewSecurityContextInd					CRITICALITY reject	TYPE NewSecurityContextInd						PRESENCE optional		}|
	{ ID id-NASC									CRITICALITY reject	TYPE NAS-PDU										PRESENCE optional		}|
	{ ID id-PDUSessionResourceSetupListHOReq		CRITICALITY reject	TYPE PDUSessionResourceSetupListHOReq			PRESENCE mandatory	}|
	{ ID id-AllowedNSSAI							CRITICALITY reject	TYPE AllowedNSSAI									PRESENCE mandatory	}|
	{ ID id-TraceActivation							CRITICALITY ignore	TYPE TraceActivation								PRESENCE optional		}|
	{ ID id-MaskedIMEISV							CRITICALITY ignore	TYPE MaskedIMEISV									PRESENCE optional		}|
	{ ID id-SourceToTarget-TransparentContainer		CRITICALITY reject	TYPE SourceToTarget-TransparentContainer		PRESENCE mandatory	}|
	{ ID id-MobilityRestrictionList					CRITICALITY ignore	TYPE MobilityRestrictionList						PRESENCE optional		}|
	{ ID id-LocationReportingRequestType			CRITICALITY ignore	TYPE LocationReportingRequestType				PRESENCE optional		}|
	{ ID id-RRCInactiveTransitionReportRequest		CRITICALITY ignore	TYPE RRCInactiveTransitionReportRequest		PRESENCE optional		}|
	{ ID id-GUAMI									CRITICALITY reject	TYPE GUAMI											PRESENCE mandatory	}|
	{ ID id-RedirectionVoiceFallback				CRITICALITY ignore	TYPE RedirectionVoiceFallback					PRESENCE optional		}|
	{ ID id-CNAssistedRANTuning						CRITICALITY ignore	TYPE CNAssistedRANTuning							PRESENCE optional		}|
	{ ID id-SRVCCOperationPossible					CRITICALITY ignore	TYPE SRVCCOperationPossible						PRESENCE optional		}|
	{ ID id-IAB-Authorized							CRITICALITY reject	TYPE IAB-Authorized									PRESENCE optional		}|
	{ ID id-Enhanced-CoverageRestriction			CRITICALITY ignore	TYPE Enhanced-CoverageRestriction				PRESENCE optional		}|
	{ ID id-UE-DifferentiationInfo					CRITICALITY ignore	TYPE UE-DifferentiationInfo						PRESENCE optional		}|
	{ ID id-NRV2XServicesAuthorized					CRITICALITY ignore	TYPE NRV2XServicesAuthorized						PRESENCE optional		}|
	{ ID id-LTEV2XServicesAuthorized				CRITICALITY ignore	TYPE LTEV2XServicesAuthorized					PRESENCE optional		}|
	{ ID id-NRUESidelinkAggregateMaximumBitrate		CRITICALITY ignore	TYPE NRUESidelinkAggregateMaximumBitrate		PRESENCE optional		}|
	{ ID id-LTEUESidelinkAggregateMaximumBitrate	CRITICALITY ignore	TYPE LTEUESidelinkAggregateMaximumBitrate	PRESENCE optional		}|
	{ ID id-PC5QoSParameters						CRITICALITY ignore	TYPE PC5QoSParameters								PRESENCE optional 	}|
	{ ID id-CEmodeBrestricted						CRITICALITY ignore	TYPE CEmodeBrestricted								PRESENCE optional		}|
	{ ID id-UE-UP-CIoT-Support						CRITICALITY ignore	TYPE UE-UP-CIoT-Support								PRESENCE optional		}|
	{ ID id-ManagementBasedMDTPLMNList				CRITICALITY ignore	TYPE MDTPLMNList									PRESENCE optional		}|
	{ ID id-UERadioCapabilityID						CRITICALITY reject	TYPE UERadioCapabilityID							PRESENCE optional		}|
	{ ID id-Extended-ConnectedTime					CRITICALITY ignore	TYPE Extended-ConnectedTime						PRESENCE optional		},
	...
}

-- **************************************************************
--
-- HANDOVER REQUEST ACKNOWLEDGE
--
-- **************************************************************

HandoverRequestAcknowledge ::= SEQUENCE {
	protocolIEs		ProtocolIE-Container		{ {HandoverRequestAcknowledgeIEs} },
	...
}

HandoverRequestAcknowledgeIEs NGAP-PROTOCOL-IES ::= {
	{ ID id-AMF-UE-NGAP-ID								CRITICALITY ignore	TYPE AMF-UE-NGAP-ID											PRESENCE mandatory	}|
	{ ID id-RAN-UE-NGAP-ID								CRITICALITY ignore	TYPE RAN-UE-NGAP-ID											PRESENCE mandatory	}|
	{ ID id-PDUSessionResourceAdmittedList				CRITICALITY ignore	TYPE PDUSessionResourceAdmittedList					PRESENCE mandatory	}|
	{ ID id-PDUSessionResourceFailedToSetupListHOAck	CRITICALITY ignore	TYPE PDUSessionResourceFailedToSetupListHOAck		PRESENCE optional		}|
	{ ID id-TargetToSource-TransparentContainer			CRITICALITY reject	TYPE TargetToSource-TransparentContainer			PRESENCE mandatory	}|
	{ ID id-CriticalityDiagnostics						CRITICALITY ignore	TYPE CriticalityDiagnostics								PRESENCE optional		},
	...
}


-- **************************************************************
--
-- HANDOVER FAILURE
--
-- **************************************************************

HandoverFailure ::= SEQUENCE {
	protocolIEs		ProtocolIE-Container		{ { HandoverFailureIEs} },
	...
}

HandoverFailureIEs NGAP-PROTOCOL-IES ::= {	
	{ ID id-AMF-UE-NGAP-ID				CRITICALITY ignore	TYPE AMF-UE-NGAP-ID				PRESENCE mandatory	}|
	{ ID id-Cause						CRITICALITY ignore	TYPE Cause						PRESENCE mandatory	}|
	{ ID id-CriticalityDiagnostics		CRITICALITY ignore	TYPE CriticalityDiagnostics		PRESENCE optional		}|
	{ ID id-TargettoSource-Failure-TransparentContainer		CRITICALITY ignore	TYPE TargettoSource-Failure-TransparentContainer		PRESENCE optional		},
	...
}

-- **************************************************************
--
-- Handover Notification Elementary Procedure
--
-- **************************************************************

-- **************************************************************
--
-- HANDOVER NOTIFY
--
-- **************************************************************

HandoverNotify ::= SEQUENCE {
	protocolIEs		ProtocolIE-Container		{ { HandoverNotifyIEs} },
	...
}

HandoverNotifyIEs NGAP-PROTOCOL-IES ::= {	
	{ ID id-AMF-UE-NGAP-ID				CRITICALITY reject	TYPE AMF-UE-NGAP-ID				PRESENCE mandatory	}|
	{ ID id-RAN-UE-NGAP-ID				CRITICALITY reject	TYPE RAN-UE-NGAP-ID				PRESENCE mandatory	}|
	{ ID id-UserLocationInformation		CRITICALITY ignore	TYPE UserLocationInformation	PRESENCE mandatory	}|
	{ ID id-NotifySourceNGRANNode		CRITICALITY ignore	TYPE NotifySourceNGRANNode		PRESENCE optional   	},
	...
}

-- **************************************************************
--
-- Path Switch Request Elementary Procedure
--
-- **************************************************************

-- **************************************************************
--
-- PATH SWITCH REQUEST
--
-- **************************************************************

PathSwitchRequest ::= SEQUENCE {
	protocolIEs		ProtocolIE-Container		{ { PathSwitchRequestIEs} },
	...
}

PathSwitchRequestIEs NGAP-PROTOCOL-IES ::= {	
	{ ID id-RAN-UE-NGAP-ID								CRITICALITY reject	TYPE RAN-UE-NGAP-ID											PRESENCE mandatory	}|
	{ ID id-SourceAMF-UE-NGAP-ID						CRITICALITY reject	TYPE AMF-UE-NGAP-ID											PRESENCE mandatory	}|
	{ ID id-UserLocationInformation						CRITICALITY ignore	TYPE UserLocationInformation							PRESENCE mandatory	}|
	{ ID id-UESecurityCapabilities						CRITICALITY ignore	TYPE UESecurityCapabilities								PRESENCE mandatory	}|
	{ ID id-PDUSessionResourceToBeSwitchedDLList		CRITICALITY reject	TYPE PDUSessionResourceToBeSwitchedDLList			PRESENCE mandatory	}|
	{ ID id-PDUSessionResourceFailedToSetupListPSReq	CRITICALITY ignore	TYPE PDUSessionResourceFailedToSetupListPSReq		PRESENCE optional		}|
	{ ID id-RRC-Resume-Cause							CRITICALITY ignore	TYPE RRCEstablishmentCause								PRESENCE optional		},
	...
}


-- **************************************************************
--
-- PATH SWITCH REQUEST ACKNOWLEDGE
--
-- **************************************************************

PathSwitchRequestAcknowledge ::= SEQUENCE {
	protocolIEs		ProtocolIE-Container		{ { PathSwitchRequestAcknowledgeIEs} },
	...
}

PathSwitchRequestAcknowledgeIEs NGAP-PROTOCOL-IES ::= {	
	{ ID id-AMF-UE-NGAP-ID								CRITICALITY ignore	TYPE AMF-UE-NGAP-ID										PRESENCE mandatory	}|
	{ ID id-RAN-UE-NGAP-ID								CRITICALITY ignore	TYPE RAN-UE-NGAP-ID										PRESENCE mandatory	}|
	{ ID id-UESecurityCapabilities						CRITICALITY reject	TYPE UESecurityCapabilities							PRESENCE optional		}|
	{ ID id-SecurityContext								CRITICALITY reject	TYPE SecurityContext									PRESENCE mandatory	}|
	{ ID id-NewSecurityContextInd						CRITICALITY reject	TYPE NewSecurityContextInd							PRESENCE optional		}|
	{ ID id-PDUSessionResourceSwitchedList				CRITICALITY ignore	TYPE PDUSessionResourceSwitchedList				PRESENCE mandatory	}|
	{ ID id-PDUSessionResourceReleasedListPSAck			CRITICALITY ignore	TYPE PDUSessionResourceReleasedListPSAck		PRESENCE optional		}|
	{ ID id-AllowedNSSAI								CRITICALITY reject	TYPE AllowedNSSAI										PRESENCE mandatory	}|
	{ ID id-CoreNetworkAssistanceInformationForInactive		CRITICALITY ignore	TYPE CoreNetworkAssistanceInformationForInactive		PRESENCE optional		}|
	{ ID id-RRCInactiveTransitionReportRequest			CRITICALITY ignore	TYPE RRCInactiveTransitionReportRequest			PRESENCE optional		}|
	{ ID id-CriticalityDiagnostics						CRITICALITY ignore	TYPE CriticalityDiagnostics							PRESENCE optional		}|
	{ ID id-RedirectionVoiceFallback					CRITICALITY ignore	TYPE RedirectionVoiceFallback						PRESENCE optional		}|
	{ ID id-CNAssistedRANTuning							CRITICALITY ignore	TYPE CNAssistedRANTuning								PRESENCE optional		}|
	{ ID id-SRVCCOperationPossible						CRITICALITY ignore	TYPE SRVCCOperationPossible							PRESENCE optional		}|
	{ ID id-Enhanced-CoverageRestriction				CRITICALITY ignore	TYPE Enhanced-CoverageRestriction					PRESENCE optional		}|
	{ ID id-Extended-ConnectedTime						CRITICALITY ignore	TYPE Extended-ConnectedTime							PRESENCE optional		}|
	{ ID id-UE-DifferentiationInfo						CRITICALITY ignore	TYPE UE-DifferentiationInfo							PRESENCE optional		}|
	{ ID id-NRV2XServicesAuthorized						CRITICALITY ignore	TYPE NRV2XServicesAuthorized						PRESENCE optional		}|
	{ ID id-LTEV2XServicesAuthorized					CRITICALITY ignore	TYPE LTEV2XServicesAuthorized						PRESENCE optional		}|
	{ ID id-NRUESidelinkAggregateMaximumBitrate			CRITICALITY ignore	TYPE NRUESidelinkAggregateMaximumBitrate		PRESENCE optional		}|
	{ ID id-LTEUESidelinkAggregateMaximumBitrate		CRITICALITY ignore	TYPE LTEUESidelinkAggregateMaximumBitrate		PRESENCE optional		}|
	{ ID id-PC5QoSParameters							CRITICALITY ignore	TYPE PC5QoSParameters									PRESENCE optional 	}|
	{ ID id-CEmodeBrestricted							CRITICALITY ignore	TYPE CEmodeBrestricted								PRESENCE optional		}|
	{ ID id-UE-UP-CIoT-Support							CRITICALITY ignore	TYPE UE-UP-CIoT-Support								PRESENCE optional		}|
	{ ID id-UERadioCapabilityID							CRITICALITY reject	TYPE UERadioCapabilityID								PRESENCE optional		},
	...
}


-- **************************************************************
--
-- PATH SWITCH REQUEST FAILURE
--
-- **************************************************************

PathSwitchRequestFailure ::= SEQUENCE {
	protocolIEs		ProtocolIE-Container		{ { PathSwitchRequestFailureIEs} },
	...
}

PathSwitchRequestFailureIEs NGAP-PROTOCOL-IES ::= {	
	{ ID id-AMF-UE-NGAP-ID							CRITICALITY ignore	TYPE AMF-UE-NGAP-ID									PRESENCE mandatory	}|
	{ ID id-RAN-UE-NGAP-ID							CRITICALITY ignore	TYPE RAN-UE-NGAP-ID									PRESENCE mandatory	}|
	{ ID id-PDUSessionResourceReleasedListPSFail	CRITICALITY ignore	TYPE PDUSessionResourceReleasedListPSFail	PRESENCE mandatory	}|
	{ ID id-CriticalityDiagnostics					CRITICALITY ignore	TYPE CriticalityDiagnostics						PRESENCE optional		},
	...
}

-- **************************************************************
--
-- Handover Cancellation Elementary Procedure
--
-- **************************************************************

-- **************************************************************
--
-- HANDOVER CANCEL
--
-- **************************************************************

HandoverCancel ::= SEQUENCE {
	protocolIEs		ProtocolIE-Container		{ { HandoverCancelIEs} },
	...
}

HandoverCancelIEs NGAP-PROTOCOL-IES ::= {	
	{ ID id-AMF-UE-NGAP-ID		CRITICALITY reject	TYPE AMF-UE-NGAP-ID		PRESENCE mandatory	}|
	{ ID id-RAN-UE-NGAP-ID		CRITICALITY reject	TYPE RAN-UE-NGAP-ID		PRESENCE mandatory	}|
	{ ID id-Cause				CRITICALITY ignore	TYPE Cause				PRESENCE mandatory	},
	...
}

-- **************************************************************
--
-- HANDOVER CANCEL ACKNOWLEDGE
--
-- **************************************************************

HandoverCancelAcknowledge ::= SEQUENCE {
	protocolIEs		ProtocolIE-Container		{ { HandoverCancelAcknowledgeIEs} },
	...
}

HandoverCancelAcknowledgeIEs NGAP-PROTOCOL-IES ::= {	
	{ ID id-AMF-UE-NGAP-ID				CRITICALITY ignore	TYPE AMF-UE-NGAP-ID				PRESENCE mandatory	}|
	{ ID id-RAN-UE-NGAP-ID				CRITICALITY ignore	TYPE RAN-UE-NGAP-ID				PRESENCE mandatory	}|
	{ ID id-CriticalityDiagnostics		CRITICALITY ignore	TYPE CriticalityDiagnostics		PRESENCE optional		},
	...
}

-- **************************************************************
--
-- HANDOVER SUCCESS ELEMENTARY PROCEDURE
--
-- **************************************************************

-- **************************************************************
--
-- HANDOVER SUCCESS
--
-- **************************************************************

HandoverSuccess ::= SEQUENCE {
	protocolIEs			ProtocolIE-Container       { { HandoverSuccessIEs} },
	...
}

HandoverSuccessIEs NGAP-PROTOCOL-IES ::= {	
	{ ID id-AMF-UE-NGAP-ID		CRITICALITY reject	TYPE AMF-UE-NGAP-ID		PRESENCE mandatory	}|
	{ ID id-RAN-UE-NGAP-ID		CRITICALITY reject	TYPE RAN-UE-NGAP-ID		PRESENCE mandatory	},
	...
}

-- **************************************************************
--
-- UPLINK RAN EARLY STATUS TRANSFER ELEMENTARY PROCEDURE
--
-- **************************************************************

-- **************************************************************
--
-- Uplink RAN Early Status Transfer
--
-- **************************************************************

UplinkRANEarlyStatusTransfer ::= SEQUENCE {
	protocolIEs			ProtocolIE-Container       { {UplinkRANEarlyStatusTransferIEs} },
	...
}

UplinkRANEarlyStatusTransferIEs NGAP-PROTOCOL-IES ::= {
	{ ID id-AMF-UE-NGAP-ID								CRITICALITY reject	TYPE AMF-UE-NGAP-ID		PRESENCE mandatory}|
	{ ID id-RAN-UE-NGAP-ID								CRITICALITY reject	TYPE RAN-UE-NGAP-ID		PRESENCE mandatory}|
	{ ID id-EarlyStatusTransfer-TransparentContainer    CRITICALITY reject  TYPE EarlyStatusTransfer-TransparentContainer	PRESENCE mandatory},
	...
}

-- **************************************************************
--
-- DOWNLINK RAN EARLY STATUS TRANSFER ELEMENTARY PROCEDURE
--
-- **************************************************************

-- **************************************************************
--
-- Downlink RAN Early Status Transfer
--
-- **************************************************************

DownlinkRANEarlyStatusTransfer ::= SEQUENCE {
	protocolIEs			ProtocolIE-Container       { {DownlinkRANEarlyStatusTransferIEs} },
	...
}

DownlinkRANEarlyStatusTransferIEs NGAP-PROTOCOL-IES ::= {
	{ ID id-AMF-UE-NGAP-ID								CRITICALITY reject	TYPE AMF-UE-NGAP-ID		PRESENCE mandatory}|
	{ ID id-RAN-UE-NGAP-ID								CRITICALITY reject	TYPE RAN-UE-NGAP-ID		PRESENCE mandatory}|
	{ ID id-EarlyStatusTransfer-TransparentContainer	CRITICALITY reject	TYPE EarlyStatusTransfer-TransparentContainer		PRESENCE mandatory},
	...
}


-- **************************************************************
--
-- Uplink RAN Status Transfer Elementary Procedure
--
-- **************************************************************

-- **************************************************************
--
-- UPLINK RAN STATUS TRANSFER
--
-- **************************************************************

UplinkRANStatusTransfer ::= SEQUENCE {
	protocolIEs		ProtocolIE-Container		{ {UplinkRANStatusTransferIEs} },
	...
}

UplinkRANStatusTransferIEs NGAP-PROTOCOL-IES ::= {
	{ ID id-AMF-UE-NGAP-ID								CRITICALITY reject	TYPE AMF-UE-NGAP-ID		PRESENCE mandatory	}|
	{ ID id-RAN-UE-NGAP-ID								CRITICALITY reject	TYPE RAN-UE-NGAP-ID		PRESENCE mandatory	}|
	{ ID id-RANStatusTransfer-TransparentContainer		CRITICALITY reject	TYPE RANStatusTransfer-TransparentContainer	PRESENCE mandatory	},
	...
}

-- **************************************************************
--
-- Downlink RAN Status Transfer Elementary Procedure
--
-- **************************************************************

-- **************************************************************
--
-- DOWNLINK RAN STATUS TRANSFER
--
-- **************************************************************

DownlinkRANStatusTransfer ::= SEQUENCE {
	protocolIEs		ProtocolIE-Container		{ {DownlinkRANStatusTransferIEs} },
	...
}

DownlinkRANStatusTransferIEs NGAP-PROTOCOL-IES ::= {
	{ ID id-AMF-UE-NGAP-ID								CRITICALITY reject	TYPE AMF-UE-NGAP-ID			PRESENCE mandatory	}|
	{ ID id-RAN-UE-NGAP-ID								CRITICALITY reject	TYPE RAN-UE-NGAP-ID			PRESENCE mandatory	}|
	{ ID id-RANStatusTransfer-TransparentContainer		CRITICALITY reject	TYPE RANStatusTransfer-TransparentContainer		PRESENCE mandatory	},
	...
}

-- **************************************************************
--
-- PAGING ELEMENTARY PROCEDURE
--
-- **************************************************************

-- **************************************************************
--
-- PAGING
--
-- **************************************************************

Paging ::= SEQUENCE {
	protocolIEs		ProtocolIE-Container		{ {PagingIEs} },
	...
}

PagingIEs NGAP-PROTOCOL-IES ::= {
	{ ID id-UEPagingIdentity				CRITICALITY ignore	TYPE UEPagingIdentity				PRESENCE mandatory	}|
	{ ID id-PagingDRX						CRITICALITY ignore	TYPE PagingDRX						PRESENCE optional		}|
	{ ID id-TAIListForPaging				CRITICALITY ignore	TYPE TAIListForPaging				PRESENCE mandatory	}|
	{ ID id-PagingPriority					CRITICALITY ignore	TYPE PagingPriority					PRESENCE optional		}|
	{ ID id-UERadioCapabilityForPaging		CRITICALITY ignore	TYPE UERadioCapabilityForPaging		PRESENCE optional		}|
	{ ID id-PagingOrigin					CRITICALITY ignore	TYPE PagingOrigin					PRESENCE optional		}|
	{ ID id-AssistanceDataForPaging			CRITICALITY ignore	TYPE AssistanceDataForPaging		PRESENCE optional		}|
	{ ID id-NB-IoT-Paging-eDRXInfo			CRITICALITY ignore	TYPE NB-IoT-Paging-eDRXInfo			PRESENCE optional		}|
	{ ID id-NB-IoT-PagingDRX				CRITICALITY ignore	TYPE NB-IoT-PagingDRX				PRESENCE optional		}|
	{ ID id-Enhanced-CoverageRestriction	CRITICALITY ignore	TYPE Enhanced-CoverageRestriction	PRESENCE optional		}|
	{ ID id-WUS-Assistance-Information		CRITICALITY ignore	TYPE WUS-Assistance-Information		PRESENCE optional		}|
	{ ID id-PagingeDRXInformation			CRITICALITY ignore	TYPE PagingeDRXInformation			PRESENCE optional		}|
	{ ID id-CEmodeBrestricted				CRITICALITY ignore	TYPE CEmodeBrestricted				PRESENCE optional		},
	...
}

-- **************************************************************
--
-- NAS TRANSPORT ELEMENTARY PROCEDURES
--
-- **************************************************************

-- **************************************************************
--
-- INITIAL UE MESSAGE
--
-- **************************************************************

InitialUEMessage ::= SEQUENCE {
	protocolIEs		ProtocolIE-Container		{ {InitialUEMessage-IEs} },
	...
}

InitialUEMessage-IEs NGAP-PROTOCOL-IES ::= {
	{ ID id-RAN-UE-NGAP-ID							CRITICALITY reject	TYPE RAN-UE-NGAP-ID									PRESENCE mandatory	}|
	{ ID id-NAS-PDU									CRITICALITY reject	TYPE NAS-PDU										PRESENCE mandatory	}|
	{ ID id-UserLocationInformation					CRITICALITY reject	TYPE UserLocationInformation						PRESENCE mandatory	}|
	{ ID id-RRCEstablishmentCause					CRITICALITY ignore	TYPE RRCEstablishmentCause						PRESENCE mandatory	}|
	{ ID id-FiveG-S-TMSI							CRITICALITY reject	TYPE FiveG-S-TMSI									PRESENCE optional		}|
	{ ID id-AMFSetID								CRITICALITY ignore	TYPE AMFSetID										PRESENCE optional		}|
	{ ID id-UEContextRequest						CRITICALITY ignore	TYPE UEContextRequest								PRESENCE optional		}|
	{ ID id-AllowedNSSAI							CRITICALITY reject	TYPE AllowedNSSAI									PRESENCE optional		}|
	{ ID id-SourceToTarget-AMFInformationReroute	CRITICALITY ignore	TYPE SourceToTarget-AMFInformationReroute	PRESENCE optional		}|
	{ ID id-SelectedPLMNIdentity					CRITICALITY ignore	TYPE PLMNIdentity									PRESENCE optional		}|
	{ ID id-IABNodeIndication						CRITICALITY reject	TYPE IABNodeIndication								PRESENCE optional		}|
	{ ID id-CEmodeBSupport-Indicator				CRITICALITY reject	TYPE CEmodeBSupport-Indicator					PRESENCE optional		}|
	{ ID id-LTEM-Indication							CRITICALITY ignore	TYPE LTEM-Indication								PRESENCE optional		}|
	{ ID id-EDT-Session								CRITICALITY ignore	TYPE EDT-Session									PRESENCE optional		}|
	{ ID id-AuthenticatedIndication					CRITICALITY ignore	TYPE AuthenticatedIndication						PRESENCE optional		}|
	{ ID id-NPN-AccessInformation					CRITICALITY reject	TYPE NPN-AccessInformation						PRESENCE optional		},
	...
}

-- **************************************************************
--
-- DOWNLINK NAS TRANSPORT
--
-- **************************************************************

DownlinkNASTransport ::= SEQUENCE {
	protocolIEs		ProtocolIE-Container		{ {DownlinkNASTransport-IEs} },
	...
}

DownlinkNASTransport-IEs NGAP-PROTOCOL-IES ::= {
	{ ID id-AMF-UE-NGAP-ID					CRITICALITY reject	TYPE AMF-UE-NGAP-ID					PRESENCE mandatory	}|
	{ ID id-RAN-UE-NGAP-ID					CRITICALITY reject	TYPE RAN-UE-NGAP-ID					PRESENCE mandatory	}|
	{ ID id-OldAMF							CRITICALITY reject	TYPE AMFName						PRESENCE optional		}|
	{ ID id-RANPagingPriority				CRITICALITY ignore	TYPE RANPagingPriority				PRESENCE optional		}|
	{ ID id-NAS-PDU							CRITICALITY reject	TYPE NAS-PDU						PRESENCE mandatory	}|
	{ ID id-MobilityRestrictionList			CRITICALITY ignore	TYPE MobilityRestrictionList		PRESENCE optional		}|
	{ ID id-IndexToRFSP						CRITICALITY ignore	TYPE IndexToRFSP					PRESENCE optional		}|
	{ ID id-UEAggregateMaximumBitRate		CRITICALITY ignore	TYPE UEAggregateMaximumBitRate		PRESENCE optional		}|
	{ ID id-AllowedNSSAI					CRITICALITY reject	TYPE AllowedNSSAI					PRESENCE optional		}|
	{ ID id-SRVCCOperationPossible			CRITICALITY ignore	TYPE SRVCCOperationPossible			PRESENCE optional		}|
	{ ID id-Enhanced-CoverageRestriction	CRITICALITY ignore	TYPE Enhanced-CoverageRestriction	PRESENCE optional		}|
	{ ID id-Extended-ConnectedTime			CRITICALITY ignore	TYPE Extended-ConnectedTime			PRESENCE optional		}|
	{ ID id-UE-DifferentiationInfo			CRITICALITY ignore	TYPE UE-DifferentiationInfo			PRESENCE optional		}|
	{ ID id-CEmodeBrestricted				CRITICALITY ignore	TYPE CEmodeBrestricted				PRESENCE optional		}|
	{ ID id-UERadioCapability				CRITICALITY ignore	TYPE UERadioCapability				PRESENCE optional		}|
	{ ID id-UECapabilityInfoRequest			CRITICALITY ignore	TYPE UECapabilityInfoRequest		PRESENCE optional		}|
	{ ID id-EndIndication					CRITICALITY ignore	TYPE EndIndication					PRESENCE optional		}|
	{ ID id-UERadioCapabilityID				CRITICALITY reject	TYPE UERadioCapabilityID			PRESENCE optional		},
	...
}

-- **************************************************************
--
-- UPLINK NAS TRANSPORT
--
-- **************************************************************

UplinkNASTransport ::= SEQUENCE {
	protocolIEs		ProtocolIE-Container	{ {UplinkNASTransport-IEs} },
	...
}

UplinkNASTransport-IEs NGAP-PROTOCOL-IES ::= {
	{ ID id-AMF-UE-NGAP-ID				CRITICALITY reject	TYPE AMF-UE-NGAP-ID					PRESENCE mandatory	}|
	{ ID id-RAN-UE-NGAP-ID				CRITICALITY reject	TYPE RAN-UE-NGAP-ID					PRESENCE mandatory	}|
	{ ID id-NAS-PDU						CRITICALITY reject	TYPE NAS-PDU						PRESENCE mandatory	}|
	{ ID id-UserLocationInformation		CRITICALITY ignore	TYPE UserLocationInformation		PRESENCE mandatory	}|
	{ ID id-W-AGFIdentityInformation	CRITICALITY reject	TYPE OCTET STRING					PRESENCE optional	}|
	{ ID id-TNGFIdentityInformation		CRITICALITY reject	TYPE OCTET STRING					PRESENCE optional	}|
	{ ID id-TWIFIdentityInformation		CRITICALITY reject	TYPE OCTET STRING					PRESENCE optional	},
	...
}

-- **************************************************************
--
-- NAS NON DELIVERY INDICATION
--
-- **************************************************************

NASNonDeliveryIndication ::= SEQUENCE {
	protocolIEs		ProtocolIE-Container		{ {NASNonDeliveryIndication-IEs} },
	...
}

NASNonDeliveryIndication-IEs NGAP-PROTOCOL-IES ::= {
	{ ID id-AMF-UE-NGAP-ID		CRITICALITY reject	TYPE AMF-UE-NGAP-ID		PRESENCE mandatory	}|
	{ ID id-RAN-UE-NGAP-ID		CRITICALITY reject	TYPE RAN-UE-NGAP-ID		PRESENCE mandatory	}|
	{ ID id-NAS-PDU				CRITICALITY ignore	TYPE NAS-PDU			PRESENCE mandatory	}|
	{ ID id-Cause				CRITICALITY ignore	TYPE Cause				PRESENCE mandatory	},
	...
}

-- **************************************************************
--
-- REROUTE NAS REQUEST
--
-- **************************************************************

RerouteNASRequest ::= SEQUENCE {
	protocolIEs		ProtocolIE-Container		{ {RerouteNASRequest-IEs} },
	...
}

RerouteNASRequest-IEs NGAP-PROTOCOL-IES ::= {
	{ ID id-RAN-UE-NGAP-ID							CRITICALITY reject	TYPE RAN-UE-NGAP-ID									PRESENCE mandatory	}|
	{ ID id-AMF-UE-NGAP-ID							CRITICALITY ignore	TYPE AMF-UE-NGAP-ID									PRESENCE optional		}|
	{ ID id-NGAP-Message							CRITICALITY reject	TYPE OCTET STRING									PRESENCE mandatory	}|
	{ ID id-AMFSetID								CRITICALITY reject	TYPE AMFSetID										PRESENCE mandatory	}|
	{ ID id-AllowedNSSAI							CRITICALITY reject	TYPE AllowedNSSAI									PRESENCE optional		}|
	{ ID id-SourceToTarget-AMFInformationReroute	CRITICALITY ignore	TYPE SourceToTarget-AMFInformationReroute	PRESENCE optional 	},
	...
}

-- **************************************************************
--
-- INTERFACE MANAGEMENT ELEMENTARY PROCEDURES
--
-- **************************************************************

-- **************************************************************
--
-- NG Setup Elementary Procedure
--
-- **************************************************************

-- **************************************************************
--
-- NG SETUP REQUEST
--
-- **************************************************************

NGSetupRequest ::= SEQUENCE {
	protocolIEs		ProtocolIE-Container		{ {NGSetupRequestIEs} },
	...
}

NGSetupRequestIEs NGAP-PROTOCOL-IES ::= {
	{ ID id-GlobalRANNodeID				CRITICALITY reject	TYPE GlobalRANNodeID				PRESENCE mandatory	}|
	{ ID id-RANNodeName					CRITICALITY ignore	TYPE RANNodeName					PRESENCE optional	}|
	{ ID id-SupportedTAList				CRITICALITY reject	TYPE SupportedTAList				PRESENCE mandatory	}|
	{ ID id-DefaultPagingDRX			CRITICALITY ignore	TYPE PagingDRX						PRESENCE mandatory	}|
	{ ID id-UERetentionInformation		CRITICALITY ignore	TYPE UERetentionInformation			PRESENCE optional	}|
	{ ID id-NB-IoT-DefaultPagingDRX		CRITICALITY ignore	TYPE NB-IoT-DefaultPagingDRX		PRESENCE optional	}|
	{ ID id-Extended-RANNodeName		CRITICALITY ignore	TYPE Extended-RANNodeName			PRESENCE optional	},
	...
}

-- **************************************************************
--
-- NG SETUP RESPONSE
--
-- **************************************************************

NGSetupResponse ::= SEQUENCE {
	protocolIEs		ProtocolIE-Container		{ {NGSetupResponseIEs} },
	...
}

NGSetupResponseIEs NGAP-PROTOCOL-IES ::= {
	{ ID id-AMFName						CRITICALITY reject	TYPE AMFName					PRESENCE mandatory	}|
	{ ID id-ServedGUAMIList				CRITICALITY reject	TYPE ServedGUAMIList			PRESENCE mandatory	}|
	{ ID id-RelativeAMFCapacity			CRITICALITY ignore	TYPE RelativeAMFCapacity		PRESENCE mandatory	}|
	{ ID id-PLMNSupportList				CRITICALITY reject	TYPE PLMNSupportList			PRESENCE mandatory	}|
	{ ID id-CriticalityDiagnostics		CRITICALITY ignore	TYPE CriticalityDiagnostics		PRESENCE optional		}|
	{ ID id-UERetentionInformation		CRITICALITY ignore	TYPE UERetentionInformation		PRESENCE optional		}|
	{ ID id-IAB-Supported				CRITICALITY ignore	TYPE IAB-Supported				PRESENCE optional		}|
	{ ID id-Extended-AMFName			CRITICALITY ignore	TYPE Extended-AMFName			PRESENCE optional		},
	...
}

-- **************************************************************
--
-- NG SETUP FAILURE
--
-- **************************************************************

NGSetupFailure ::= SEQUENCE {
	protocolIEs		ProtocolIE-Container		{ {NGSetupFailureIEs} },
	...
}

NGSetupFailureIEs NGAP-PROTOCOL-IES ::= {
	{ ID id-Cause						CRITICALITY ignore	TYPE Cause						PRESENCE mandatory	}|
	{ ID id-TimeToWait					CRITICALITY ignore	TYPE TimeToWait					PRESENCE optional		}|
	{ ID id-CriticalityDiagnostics		CRITICALITY ignore	TYPE CriticalityDiagnostics		PRESENCE optional		},
	...
}

-- **************************************************************
--
-- RAN Configuration Update Elementary Procedure
--
-- **************************************************************

-- **************************************************************
--
-- RAN CONFIGURATION UPDATE 
--
-- **************************************************************

RANConfigurationUpdate ::= SEQUENCE {
	protocolIEs		ProtocolIE-Container		{ {RANConfigurationUpdateIEs} },
	...
}

RANConfigurationUpdateIEs NGAP-PROTOCOL-IES ::= {
	{ ID id-RANNodeName								CRITICALITY ignore	TYPE RANNodeName									PRESENCE optional	}|
	{ ID id-SupportedTAList							CRITICALITY reject	TYPE SupportedTAList								PRESENCE optional	}|
	{ ID id-DefaultPagingDRX						CRITICALITY ignore	TYPE PagingDRX										PRESENCE optional	}|
	{ ID id-GlobalRANNodeID							CRITICALITY ignore	TYPE GlobalRANNodeID								PRESENCE optional	}|
	{ ID id-NGRAN-TNLAssociationToRemoveList		CRITICALITY reject	TYPE NGRAN-TNLAssociationToRemoveList			PRESENCE optional	}|
	{ ID id-NB-IoT-DefaultPagingDRX					CRITICALITY ignore	TYPE NB-IoT-DefaultPagingDRX						PRESENCE optional	}|
	{ ID id-Extended-RANNodeName					CRITICALITY ignore	TYPE Extended-RANNodeName							PRESENCE optional	},
	...
}

-- **************************************************************
--
-- RAN CONFIGURATION UPDATE ACKNOWLEDGE
--
-- **************************************************************

RANConfigurationUpdateAcknowledge ::= SEQUENCE {
	protocolIEs		ProtocolIE-Container		{ {RANConfigurationUpdateAcknowledgeIEs} },
	...
}

RANConfigurationUpdateAcknowledgeIEs NGAP-PROTOCOL-IES ::= {
	{ ID id-CriticalityDiagnostics		CRITICALITY ignore	TYPE CriticalityDiagnostics		PRESENCE optional		},
	...
}

-- **************************************************************
--
-- RAN CONFIGURATION UPDATE FAILURE
--
-- **************************************************************

RANConfigurationUpdateFailure ::= SEQUENCE {
	protocolIEs		ProtocolIE-Container		{ {RANConfigurationUpdateFailureIEs} },
	...
}

RANConfigurationUpdateFailureIEs NGAP-PROTOCOL-IES ::= {
	{ ID id-Cause						CRITICALITY ignore	TYPE Cause						PRESENCE mandatory	}|
	{ ID id-TimeToWait					CRITICALITY ignore	TYPE TimeToWait					PRESENCE optional		}|
	{ ID id-CriticalityDiagnostics		CRITICALITY ignore	TYPE CriticalityDiagnostics		PRESENCE optional		},
...
}

-- **************************************************************
--
-- AMF Configuration Update Elementary Procedure
--
-- **************************************************************

-- **************************************************************
--
-- AMF CONFIGURATION UPDATE 
--
-- **************************************************************

AMFConfigurationUpdate ::= SEQUENCE {
	protocolIEs		ProtocolIE-Container		{ {AMFConfigurationUpdateIEs} },
	...
}

AMFConfigurationUpdateIEs NGAP-PROTOCOL-IES ::= {
	{ ID id-AMFName								CRITICALITY reject	TYPE AMFName								PRESENCE optional		}|
	{ ID id-ServedGUAMIList						CRITICALITY reject	TYPE ServedGUAMIList						PRESENCE optional		}|
	{ ID id-RelativeAMFCapacity					CRITICALITY ignore	TYPE RelativeAMFCapacity					PRESENCE optional		}|
	{ ID id-PLMNSupportList						CRITICALITY reject	TYPE PLMNSupportList						PRESENCE optional		}|
	{ ID id-AMF-TNLAssociationToAddList			CRITICALITY ignore	TYPE AMF-TNLAssociationToAddList			PRESENCE optional		}|
	{ ID id-AMF-TNLAssociationToRemoveList		CRITICALITY ignore	TYPE AMF-TNLAssociationToRemoveList		PRESENCE optional		}|
	{ ID id-AMF-TNLAssociationToUpdateList		CRITICALITY ignore	TYPE AMF-TNLAssociationToUpdateList		PRESENCE optional		}|
	{ ID id-Extended-AMFName					CRITICALITY ignore	TYPE Extended-AMFName						PRESENCE optional		},
	...
}

-- **************************************************************
--
-- AMF CONFIGURATION UPDATE ACKNOWLEDGE
--
-- **************************************************************

AMFConfigurationUpdateAcknowledge ::= SEQUENCE {
	protocolIEs		ProtocolIE-Container		{ {AMFConfigurationUpdateAcknowledgeIEs} },
	...
}

AMFConfigurationUpdateAcknowledgeIEs NGAP-PROTOCOL-IES ::= {
	{ ID id-AMF-TNLAssociationSetupList				CRITICALITY ignore	TYPE AMF-TNLAssociationSetupList			PRESENCE optional		}|
	{ ID id-AMF-TNLAssociationFailedToSetupList		CRITICALITY ignore	TYPE TNLAssociationList							PRESENCE optional		}|
	{ ID id-CriticalityDiagnostics					CRITICALITY ignore	TYPE CriticalityDiagnostics					PRESENCE optional		},
	...
}

-- **************************************************************
--
-- AMF CONFIGURATION UPDATE FAILURE
--
-- **************************************************************

AMFConfigurationUpdateFailure ::= SEQUENCE {
	protocolIEs		ProtocolIE-Container		{ {AMFConfigurationUpdateFailureIEs} },
	...
}

AMFConfigurationUpdateFailureIEs NGAP-PROTOCOL-IES ::= {
	{ ID id-Cause						CRITICALITY ignore	TYPE Cause						PRESENCE mandatory	}|
	{ ID id-TimeToWait					CRITICALITY ignore	TYPE TimeToWait					PRESENCE optional		}|
	{ ID id-CriticalityDiagnostics		CRITICALITY ignore	TYPE CriticalityDiagnostics		PRESENCE optional		},
	...
}

-- **************************************************************
--
-- AMF Status Indication Elementary Procedure
--
-- **************************************************************

-- **************************************************************
--
-- AMF STATUS INDICATION
--
-- **************************************************************

AMFStatusIndication ::= SEQUENCE {
	protocolIEs		ProtocolIE-Container		{ {AMFStatusIndicationIEs} },
	...
}

AMFStatusIndicationIEs NGAP-PROTOCOL-IES ::= {
	{ ID id-UnavailableGUAMIList		CRITICALITY reject	TYPE UnavailableGUAMIList		PRESENCE mandatory	},
	...
}

-- **************************************************************
--
-- NG Reset Elementary Procedure
--
-- **************************************************************

-- **************************************************************
--
-- NG RESET
--
-- **************************************************************

NGReset ::= SEQUENCE {
	protocolIEs		ProtocolIE-Container		{ {NGResetIEs} },
	...
}

NGResetIEs NGAP-PROTOCOL-IES ::= {
	{ ID id-Cause						CRITICALITY ignore	TYPE Cause						PRESENCE mandatory	}|
	{ ID id-ResetType					CRITICALITY reject	TYPE ResetType					PRESENCE mandatory	},
	...
}

-- **************************************************************
--
-- NG RESET ACKNOWLEDGE
--
-- **************************************************************

NGResetAcknowledge ::= SEQUENCE {
	protocolIEs		ProtocolIE-Container		{ {NGResetAcknowledgeIEs} },
	...
}

NGResetAcknowledgeIEs NGAP-PROTOCOL-IES ::= {
	{ ID id-UE-associatedLogicalNG-connectionList			CRITICALITY ignore	TYPE UE-associatedLogicalNG-connectionList			PRESENCE optional	}|
	{ ID id-CriticalityDiagnostics							CRITICALITY ignore	TYPE CriticalityDiagnostics								PRESENCE optional	},
	...
}

-- **************************************************************
--
-- Error Indication Elementary Procedure
--
-- **************************************************************

-- **************************************************************
--
-- ERROR INDICATION
--
-- **************************************************************

ErrorIndication ::= SEQUENCE {
	protocolIEs		ProtocolIE-Container		{ {ErrorIndicationIEs} },
	...
}

ErrorIndicationIEs NGAP-PROTOCOL-IES ::= {
	{ ID id-AMF-UE-NGAP-ID				CRITICALITY ignore	TYPE AMF-UE-NGAP-ID				PRESENCE optional		}|
	{ ID id-RAN-UE-NGAP-ID				CRITICALITY ignore	TYPE RAN-UE-NGAP-ID				PRESENCE optional		}|
	{ ID id-Cause						CRITICALITY ignore	TYPE Cause						PRESENCE optional		}|
	{ ID id-CriticalityDiagnostics		CRITICALITY ignore	TYPE CriticalityDiagnostics		PRESENCE optional		}|
	{ ID id-FiveG-S-TMSI				CRITICALITY ignore	TYPE FiveG-S-TMSI				PRESENCE optional		},
	...
}

-- **************************************************************
--
-- OVERLOAD START
--
-- **************************************************************

OverloadStart ::= SEQUENCE {
	protocolIEs		ProtocolIE-Container		{ {OverloadStartIEs} },
	...
}

OverloadStartIEs NGAP-PROTOCOL-IES ::= {	
	{ ID id-AMFOverloadResponse						CRITICALITY reject	TYPE OverloadResponse							PRESENCE optional 	}|
	{ ID id-AMFTrafficLoadReductionIndication		CRITICALITY ignore	TYPE TrafficLoadReductionIndication		PRESENCE optional		}|
	{ ID id-OverloadStartNSSAIList					CRITICALITY ignore	TYPE OverloadStartNSSAIList					PRESENCE optional		},
	...
}

-- **************************************************************
--
-- OVERLOAD STOP
--
-- **************************************************************

OverloadStop ::= SEQUENCE {
	protocolIEs		ProtocolIE-Container		{ {OverloadStopIEs} },
	...
}

OverloadStopIEs NGAP-PROTOCOL-IES ::= {	
	...
}

-- **************************************************************
--
-- CONFIGURATION TRANSFER ELEMENTARY PROCEDURES
--
-- **************************************************************

-- **************************************************************
--
-- UPLINK RAN CONFIGURATION TRANSFER
--
-- **************************************************************

UplinkRANConfigurationTransfer ::= SEQUENCE {
	protocolIEs		ProtocolIE-Container		{ {UplinkRANConfigurationTransferIEs} },
	...
}

UplinkRANConfigurationTransferIEs NGAP-PROTOCOL-IES ::= {
	{ ID id-SONConfigurationTransferUL					CRITICALITY ignore	TYPE SONConfigurationTransfer						PRESENCE optional		}|
	{ ID id-ENDC-SONConfigurationTransferUL				CRITICALITY ignore	TYPE EN-DCSONConfigurationTransfer				PRESENCE optional		}|
	{ ID id-IntersystemSONConfigurationTransferUL		CRITICALITY ignore	TYPE IntersystemSONConfigurationTransfer		PRESENCE optional		},
	...
}

-- **************************************************************
--
-- DOWNLINK RAN CONFIGURATION TRANSFER
--
-- **************************************************************

DownlinkRANConfigurationTransfer ::= SEQUENCE {
	protocolIEs		ProtocolIE-Container		{ {DownlinkRANConfigurationTransferIEs} },
	...
}

DownlinkRANConfigurationTransferIEs NGAP-PROTOCOL-IES ::= {
	{ ID id-SONConfigurationTransferDL					CRITICALITY ignore	TYPE SONConfigurationTransfer						PRESENCE optional		}|
	{ ID id-ENDC-SONConfigurationTransferDL				CRITICALITY ignore	TYPE EN-DCSONConfigurationTransfer				PRESENCE optional		}|
	{ ID id-IntersystemSONConfigurationTransferDL		CRITICALITY ignore	TYPE IntersystemSONConfigurationTransfer		PRESENCE optional		},
	...
}

-- **************************************************************
--
-- WARNING MESSAGE TRANSMISSION ELEMENTARY PROCEDURES 
--
-- **************************************************************

-- **************************************************************
--
-- Write-Replace Warning Elementary Procedure
--
-- **************************************************************

-- **************************************************************
--
-- WRITE-REPLACE WARNING REQUEST
--
-- **************************************************************

WriteReplaceWarningRequest ::= SEQUENCE {
	protocolIEs		ProtocolIE-Container		{ {WriteReplaceWarningRequestIEs} },
	...
}

WriteReplaceWarningRequestIEs NGAP-PROTOCOL-IES ::= {	
	{ ID id-MessageIdentifier				CRITICALITY reject	TYPE MessageIdentifier					PRESENCE mandatory	}|
	{ ID id-SerialNumber					CRITICALITY reject	TYPE SerialNumber						PRESENCE mandatory	}|
	{ ID id-WarningAreaList					CRITICALITY ignore	TYPE WarningAreaList					PRESENCE optional		}|
	{ ID id-RepetitionPeriod				CRITICALITY reject	TYPE RepetitionPeriod					PRESENCE mandatory	}|
	{ ID id-NumberOfBroadcastsRequested		CRITICALITY reject	TYPE NumberOfBroadcastsRequested		PRESENCE mandatory	}|
	{ ID id-WarningType						CRITICALITY ignore	TYPE WarningType						PRESENCE optional		}|
	{ ID id-WarningSecurityInfo				CRITICALITY ignore	TYPE WarningSecurityInfo				PRESENCE optional		}|
	{ ID id-DataCodingScheme				CRITICALITY ignore	TYPE DataCodingScheme					PRESENCE optional		}|
	{ ID id-WarningMessageContents			CRITICALITY ignore	TYPE WarningMessageContents				PRESENCE optional		}|
	{ ID id-ConcurrentWarningMessageInd		CRITICALITY reject	TYPE ConcurrentWarningMessageInd		PRESENCE optional		}|
	{ ID id-WarningAreaCoordinates			CRITICALITY ignore	TYPE WarningAreaCoordinates				PRESENCE optional		},
	...
}

-- **************************************************************
--
-- WRITE-REPLACE WARNING RESPONSE
--
-- **************************************************************

WriteReplaceWarningResponse ::= SEQUENCE {
	protocolIEs			ProtocolIE-Container		{ {WriteReplaceWarningResponseIEs} },
	...
}

WriteReplaceWarningResponseIEs NGAP-PROTOCOL-IES ::= {
	{ ID id-MessageIdentifier				CRITICALITY reject	TYPE MessageIdentifier					PRESENCE mandatory	}|
	{ ID id-SerialNumber					CRITICALITY reject	TYPE SerialNumber						PRESENCE mandatory	}|
	{ ID id-BroadcastCompletedAreaList		CRITICALITY ignore	TYPE BroadcastCompletedAreaList			PRESENCE optional		}|
	{ ID id-CriticalityDiagnostics			CRITICALITY ignore	TYPE CriticalityDiagnostics				PRESENCE optional		},
	...
}

-- **************************************************************
--
-- PWS Cancel Elementary Procedure
--
-- **************************************************************

-- **************************************************************
--
-- PWS CANCEL REQUEST
--
-- **************************************************************

PWSCancelRequest ::= SEQUENCE {
	protocolIEs		ProtocolIE-Container		{ {PWSCancelRequestIEs} },
	...
}

PWSCancelRequestIEs NGAP-PROTOCOL-IES ::= {	
	{ ID id-MessageIdentifier			CRITICALITY reject	TYPE MessageIdentifier				PRESENCE mandatory	}|
	{ ID id-SerialNumber				CRITICALITY reject	TYPE SerialNumber					PRESENCE mandatory	}|
	{ ID id-WarningAreaList				CRITICALITY ignore	TYPE WarningAreaList				PRESENCE optional	}|
	{ ID id-CancelAllWarningMessages	CRITICALITY reject	TYPE CancelAllWarningMessages		PRESENCE optional	},
	...
}

-- **************************************************************
--
-- PWS CANCEL RESPONSE
--
-- **************************************************************

PWSCancelResponse ::= SEQUENCE {
	protocolIEs		ProtocolIE-Container		{ {PWSCancelResponseIEs} },
	...
}

PWSCancelResponseIEs NGAP-PROTOCOL-IES ::= {
	{ ID id-MessageIdentifier			CRITICALITY reject	TYPE MessageIdentifier				PRESENCE mandatory	}|
	{ ID id-SerialNumber				CRITICALITY reject	TYPE SerialNumber					PRESENCE mandatory	}|
	{ ID id-BroadcastCancelledAreaList	CRITICALITY ignore	TYPE BroadcastCancelledAreaList		PRESENCE optional	}|
	{ ID id-CriticalityDiagnostics		CRITICALITY ignore	TYPE CriticalityDiagnostics			PRESENCE optional	},
	...
}

-- **************************************************************
--
-- PWS Restart Indication Elementary Procedure
--
-- **************************************************************

-- **************************************************************
--
-- PWS RESTART INDICATION
--
-- **************************************************************

PWSRestartIndication ::= SEQUENCE {
	protocolIEs		ProtocolIE-Container		{ {PWSRestartIndicationIEs} },
	...
}

PWSRestartIndicationIEs NGAP-PROTOCOL-IES ::= {
	{ ID id-CellIDListForRestart			CRITICALITY reject	TYPE CellIDListForRestart				PRESENCE mandatory	}|
	{ ID id-GlobalRANNodeID					CRITICALITY reject	TYPE GlobalRANNodeID					PRESENCE mandatory	}|
	{ ID id-TAIListForRestart				CRITICALITY reject	TYPE TAIListForRestart					PRESENCE mandatory	}|
	{ ID id-EmergencyAreaIDListForRestart	CRITICALITY reject	TYPE EmergencyAreaIDListForRestart	PRESENCE optional		},
	...
}

-- **************************************************************
--
-- PWS Failure Indication Elementary Procedure
--
-- **************************************************************

-- **************************************************************
--
-- PWS FAILURE INDICATION
--
-- **************************************************************

PWSFailureIndication ::= SEQUENCE {
	protocolIEs		ProtocolIE-Container		{ {PWSFailureIndicationIEs} },
	...
}

PWSFailureIndicationIEs NGAP-PROTOCOL-IES ::= {
	{ ID id-PWSFailedCellIDList			CRITICALITY reject	TYPE PWSFailedCellIDList	PRESENCE mandatory	}|
	{ ID id-GlobalRANNodeID				CRITICALITY reject	TYPE GlobalRANNodeID		PRESENCE mandatory	},
	...
}

-- **************************************************************
--
-- NRPPA TRANSPORT ELEMENTARY PROCEDURES
--
-- **************************************************************

-- **************************************************************
--
-- DOWNLINK UE ASSOCIATED NRPPA TRANSPORT
--
-- **************************************************************

DownlinkUEAssociatedNRPPaTransport ::= SEQUENCE {
	protocolIEs		ProtocolIE-Container		{ {DownlinkUEAssociatedNRPPaTransportIEs} },
	...
}

DownlinkUEAssociatedNRPPaTransportIEs NGAP-PROTOCOL-IES ::= {
	{ ID id-AMF-UE-NGAP-ID			CRITICALITY reject	TYPE AMF-UE-NGAP-ID				PRESENCE mandatory	}|
	{ ID id-RAN-UE-NGAP-ID			CRITICALITY reject	TYPE RAN-UE-NGAP-ID				PRESENCE mandatory	}|
	{ ID id-RoutingID				CRITICALITY reject	TYPE RoutingID					PRESENCE mandatory	}|
	{ ID id-NRPPa-PDU				CRITICALITY reject	TYPE NRPPa-PDU					PRESENCE mandatory	},
	...
}

-- **************************************************************
--
-- UPLINK UE ASSOCIATED NRPPA TRANSPORT
--
-- **************************************************************

UplinkUEAssociatedNRPPaTransport ::= SEQUENCE {
	protocolIEs		ProtocolIE-Container		{ {UplinkUEAssociatedNRPPaTransportIEs} },
	...
}

UplinkUEAssociatedNRPPaTransportIEs NGAP-PROTOCOL-IES ::= {
	{ ID id-AMF-UE-NGAP-ID			CRITICALITY reject	TYPE AMF-UE-NGAP-ID				PRESENCE mandatory	}|
	{ ID id-RAN-UE-NGAP-ID			CRITICALITY reject	TYPE RAN-UE-NGAP-ID				PRESENCE mandatory	}|
	{ ID id-RoutingID				CRITICALITY reject	TYPE RoutingID					PRESENCE mandatory	}|
	{ ID id-NRPPa-PDU				CRITICALITY reject	TYPE NRPPa-PDU					PRESENCE mandatory	},
	...
}

-- **************************************************************
--
-- DOWNLINK NON UE ASSOCIATED NRPPA TRANSPORT
--
-- **************************************************************

DownlinkNonUEAssociatedNRPPaTransport ::= SEQUENCE {
	protocolIEs		ProtocolIE-Container		{ {DownlinkNonUEAssociatedNRPPaTransportIEs} },
	...
}

DownlinkNonUEAssociatedNRPPaTransportIEs NGAP-PROTOCOL-IES ::= {
	{ ID id-RoutingID				CRITICALITY reject	TYPE RoutingID					PRESENCE mandatory	}|
	{ ID id-NRPPa-PDU				CRITICALITY reject	TYPE NRPPa-PDU					PRESENCE mandatory	},
	...
}

-- **************************************************************
--
-- UPLINK NON UE ASSOCIATED NRPPA TRANSPORT
--
-- **************************************************************

UplinkNonUEAssociatedNRPPaTransport ::= SEQUENCE {
	protocolIEs		ProtocolIE-Container		{ {UplinkNonUEAssociatedNRPPaTransportIEs} },
	...
}

UplinkNonUEAssociatedNRPPaTransportIEs NGAP-PROTOCOL-IES ::= {
	{ ID id-RoutingID				CRITICALITY reject	TYPE RoutingID					PRESENCE mandatory	}|
	{ ID id-NRPPa-PDU				CRITICALITY reject	TYPE NRPPa-PDU					PRESENCE mandatory	},
	...
}

-- **************************************************************
--
-- TRACE ELEMENTARY PROCEDURES
--
-- **************************************************************

-- **************************************************************
--
-- TRACE START
--
-- **************************************************************

TraceStart ::= SEQUENCE {
	protocolIEs		ProtocolIE-Container		{ {TraceStartIEs} },
	...
}

TraceStartIEs NGAP-PROTOCOL-IES ::= {
	{ ID id-AMF-UE-NGAP-ID				CRITICALITY reject	TYPE AMF-UE-NGAP-ID				PRESENCE mandatory	}|
	{ ID id-RAN-UE-NGAP-ID				CRITICALITY reject	TYPE RAN-UE-NGAP-ID				PRESENCE mandatory	}|
	{ ID id-TraceActivation				CRITICALITY ignore	TYPE TraceActivation			PRESENCE mandatory	},
	...
}

-- **************************************************************
--
-- TRACE FAILURE INDICATION
--
-- **************************************************************

TraceFailureIndication ::= SEQUENCE {
	protocolIEs		ProtocolIE-Container		{ {TraceFailureIndicationIEs} },
	...
}

TraceFailureIndicationIEs NGAP-PROTOCOL-IES ::= {
	{ ID id-AMF-UE-NGAP-ID				CRITICALITY reject	TYPE AMF-UE-NGAP-ID				PRESENCE mandatory	}|
	{ ID id-RAN-UE-NGAP-ID				CRITICALITY reject	TYPE RAN-UE-NGAP-ID				PRESENCE mandatory	}|
	{ ID id-NGRANTraceID				CRITICALITY ignore	TYPE NGRANTraceID				PRESENCE mandatory	}|
	{ ID id-Cause						CRITICALITY ignore	TYPE Cause						PRESENCE mandatory	},
	...
}

-- **************************************************************
--
-- DEACTIVATE TRACE
--
-- **************************************************************

DeactivateTrace ::= SEQUENCE {
	protocolIEs		ProtocolIE-Container		{ {DeactivateTraceIEs} },
	...
}

DeactivateTraceIEs NGAP-PROTOCOL-IES ::= {
	{ ID id-AMF-UE-NGAP-ID				CRITICALITY reject	TYPE AMF-UE-NGAP-ID				PRESENCE mandatory	}|
	{ ID id-RAN-UE-NGAP-ID				CRITICALITY reject	TYPE RAN-UE-NGAP-ID				PRESENCE mandatory	}|
	{ ID id-NGRANTraceID				CRITICALITY ignore	TYPE NGRANTraceID				PRESENCE mandatory	},
	...
}

-- **************************************************************
--
-- CELL TRAFFIC TRACE
--
-- **************************************************************

CellTrafficTrace ::= SEQUENCE {
	protocolIEs		ProtocolIE-Container		{ {CellTrafficTraceIEs} },
	...
}

CellTrafficTraceIEs NGAP-PROTOCOL-IES ::= {
	{ID id-AMF-UE-NGAP-ID					CRITICALITY reject	TYPE AMF-UE-NGAP-ID				PRESENCE mandatory	}|
	{ID id-RAN-UE-NGAP-ID					CRITICALITY reject	TYPE RAN-UE-NGAP-ID				PRESENCE mandatory	}|
	{ID id-NGRANTraceID						CRITICALITY ignore	TYPE NGRANTraceID				PRESENCE mandatory	}|
	{ID id-NGRAN-CGI						CRITICALITY ignore	TYPE NGRAN-CGI					PRESENCE mandatory	}|
	{ID id-TraceCollectionEntityIPAddress	CRITICALITY ignore	TYPE TransportLayerAddress		PRESENCE mandatory	}|
	{ID id-PrivacyIndicator					CRITICALITY ignore	TYPE PrivacyIndicator			PRESENCE optional	}|
	{ID id-TraceCollectionEntityURI			CRITICALITY ignore	TYPE URI-address				PRESENCE optional	},
	...
}

-- **************************************************************
--
-- LOCATION REPORTING ELEMENTARY PROCEDURES
--
-- **************************************************************

-- **************************************************************
--
-- LOCATION REPORTING CONTROL
--
-- **************************************************************

LocationReportingControl ::= SEQUENCE {
	protocolIEs			ProtocolIE-Container		{ {LocationReportingControlIEs} },
	...
}

LocationReportingControlIEs NGAP-PROTOCOL-IES ::= {
	{ ID id-AMF-UE-NGAP-ID					CRITICALITY reject	TYPE AMF-UE-NGAP-ID						PRESENCE mandatory	}|
	{ ID id-RAN-UE-NGAP-ID					CRITICALITY reject	TYPE RAN-UE-NGAP-ID						PRESENCE mandatory	}|
	{ ID id-LocationReportingRequestType	CRITICALITY ignore	TYPE LocationReportingRequestType		PRESENCE mandatory	},
	...
}

-- **************************************************************
--
-- LOCATION REPORTING FAILURE INDICATION
--
-- **************************************************************

LocationReportingFailureIndication ::= SEQUENCE {
	protocolIEs			ProtocolIE-Container		{ {LocationReportingFailureIndicationIEs} },
	...
}

LocationReportingFailureIndicationIEs NGAP-PROTOCOL-IES ::= {
	{ ID id-AMF-UE-NGAP-ID			CRITICALITY reject	TYPE AMF-UE-NGAP-ID				PRESENCE mandatory	}|
	{ ID id-RAN-UE-NGAP-ID			CRITICALITY reject	TYPE RAN-UE-NGAP-ID				PRESENCE mandatory	}|
	{ ID id-Cause					CRITICALITY ignore	TYPE Cause						PRESENCE mandatory	},
	...
}

-- **************************************************************
--
-- LOCATION REPORT
--
-- **************************************************************

LocationReport ::= SEQUENCE {
	protocolIEs			ProtocolIE-Container		{ {LocationReportIEs} },
	...
}

LocationReportIEs NGAP-PROTOCOL-IES ::= {
	{ ID id-AMF-UE-NGAP-ID						CRITICALITY reject	TYPE AMF-UE-NGAP-ID							PRESENCE mandatory	}|
	{ ID id-RAN-UE-NGAP-ID						CRITICALITY reject	TYPE RAN-UE-NGAP-ID							PRESENCE mandatory	}|
	{ ID id-UserLocationInformation				CRITICALITY ignore	TYPE UserLocationInformation				PRESENCE mandatory	}|
	{ ID id-UEPresenceInAreaOfInterestList		CRITICALITY ignore	TYPE UEPresenceInAreaOfInterestList		PRESENCE optional		}|
	{ ID id-LocationReportingRequestType		CRITICALITY ignore	TYPE LocationReportingRequestType		PRESENCE mandatory	},
	...
}

-- **************************************************************
--
-- UE TNLA BINDING ELEMENTARY PROCEDURES
--
-- **************************************************************

-- **************************************************************
--
-- UE TNLA BINDING RELEASE REQUEST
--
-- **************************************************************

UETNLABindingReleaseRequest ::= SEQUENCE {
	protocolIEs			ProtocolIE-Container		{ {UETNLABindingReleaseRequestIEs} },
	...
}

UETNLABindingReleaseRequestIEs NGAP-PROTOCOL-IES ::= {
	{ ID id-AMF-UE-NGAP-ID		CRITICALITY reject	TYPE AMF-UE-NGAP-ID		PRESENCE mandatory	}|
	{ ID id-RAN-UE-NGAP-ID		CRITICALITY reject	TYPE RAN-UE-NGAP-ID		PRESENCE mandatory	},
	...
}

-- **************************************************************
--
-- UE RADIO CAPABILITY MANAGEMENT ELEMENTARY PROCEDURES
--
-- **************************************************************

-- **************************************************************
--
-- UE RADIO CAPABILITY INFO INDICATION
--
-- **************************************************************

UERadioCapabilityInfoIndication ::= SEQUENCE {
	protocolIEs			ProtocolIE-Container		{ {UERadioCapabilityInfoIndicationIEs} },
	...
}

UERadioCapabilityInfoIndicationIEs NGAP-PROTOCOL-IES ::= {
	{ ID id-AMF-UE-NGAP-ID					CRITICALITY reject	TYPE AMF-UE-NGAP-ID					PRESENCE mandatory	}|
	{ ID id-RAN-UE-NGAP-ID					CRITICALITY reject	TYPE RAN-UE-NGAP-ID					PRESENCE mandatory	}|
	{ ID id-UERadioCapability				CRITICALITY ignore	TYPE UERadioCapability				PRESENCE mandatory	}|
	{ ID id-UERadioCapabilityForPaging		CRITICALITY ignore	TYPE UERadioCapabilityForPaging		PRESENCE optional		}|
	{ ID id-UERadioCapability-EUTRA-Format	CRITICALITY ignore	TYPE UERadioCapability				PRESENCE optional		},
	...
}

-- **************************************************************
--
-- UE Radio Capability Check Elementary Procedure
--
-- **************************************************************

-- **************************************************************
--
-- UE RADIO CAPABILITY CHECK REQUEST
--
-- **************************************************************

UERadioCapabilityCheckRequest ::= SEQUENCE {
	protocolIEs		ProtocolIE-Container		{ {UERadioCapabilityCheckRequestIEs} },
	...
}

UERadioCapabilityCheckRequestIEs NGAP-PROTOCOL-IES ::= {	
	{ ID id-AMF-UE-NGAP-ID			CRITICALITY reject	TYPE AMF-UE-NGAP-ID			PRESENCE mandatory	}|
	{ ID id-RAN-UE-NGAP-ID			CRITICALITY reject	TYPE RAN-UE-NGAP-ID			PRESENCE mandatory	}|
	{ ID id-UERadioCapability		CRITICALITY ignore	TYPE UERadioCapability		PRESENCE optional	}|
	{ ID id-UERadioCapabilityID		CRITICALITY reject	TYPE UERadioCapabilityID	PRESENCE optional	},
	...
}

-- **************************************************************
--
-- UE RADIO CAPABILITY CHECK RESPONSE
--
-- **************************************************************

UERadioCapabilityCheckResponse ::= SEQUENCE {
	protocolIEs		ProtocolIE-Container		{ {UERadioCapabilityCheckResponseIEs} },
	...
}

UERadioCapabilityCheckResponseIEs NGAP-PROTOCOL-IES ::= {	
	{ ID id-AMF-UE-NGAP-ID					CRITICALITY ignore	TYPE AMF-UE-NGAP-ID					PRESENCE mandatory	}|
	{ ID id-RAN-UE-NGAP-ID					CRITICALITY ignore	TYPE RAN-UE-NGAP-ID					PRESENCE mandatory	}|
	{ ID id-IMSVoiceSupportIndicator		CRITICALITY reject	TYPE IMSVoiceSupportIndicator		PRESENCE mandatory	}|
	{ ID id-CriticalityDiagnostics			CRITICALITY ignore	TYPE CriticalityDiagnostics			PRESENCE optional		},
	...
}

-- **************************************************************
--
-- PRIVATE MESSAGE ELEMENTARY PROCEDURE
--
-- **************************************************************

-- **************************************************************
--
-- PRIVATE MESSAGE
--
-- **************************************************************

PrivateMessage ::= SEQUENCE {
	privateIEs		PrivateIE-Container		{ { PrivateMessageIEs } },
	...
}

PrivateMessageIEs NGAP-PRIVATE-IES ::= {
	...
}


-- **************************************************************
--
-- DATA USAGE REPORTING ELEMENTARY PROCEDURES
--
-- **************************************************************

-- **************************************************************
--
-- SECONDARY RAT DATA USAGE REPORT
--
-- **************************************************************

SecondaryRATDataUsageReport ::= SEQUENCE {
	protocolIEs		ProtocolIE-Container		{ {SecondaryRATDataUsageReportIEs} },
	...
}

SecondaryRATDataUsageReportIEs NGAP-PROTOCOL-IES ::= {
	{ ID id-AMF-UE-NGAP-ID								CRITICALITY ignore	TYPE AMF-UE-NGAP-ID												PRESENCE mandatory	}|
	{ ID id-RAN-UE-NGAP-ID								CRITICALITY ignore	TYPE RAN-UE-NGAP-ID												PRESENCE mandatory	}|
	{ ID id-PDUSessionResourceSecondaryRATUsageList		CRITICALITY ignore	TYPE PDUSessionResourceSecondaryRATUsageList			PRESENCE mandatory	}|
	{ ID id-HandoverFlag								CRITICALITY ignore	TYPE HandoverFlag												PRESENCE optional		}|
	{ ID id-UserLocationInformation						CRITICALITY ignore	TYPE UserLocationInformation								PRESENCE optional 	},
	...
}

-- **************************************************************
--
-- RIM INFORMATION TRANSFER ELEMENTARY PROCEDURES
--
-- **************************************************************

-- **************************************************************
--
-- UPLINK RIM INFORMATION TRANSFER
--
-- **************************************************************

UplinkRIMInformationTransfer ::= SEQUENCE {
	protocolIEs		ProtocolIE-Container		{ {UplinkRIMInformationTransferIEs} },
	...
}

UplinkRIMInformationTransferIEs NGAP-PROTOCOL-IES ::= {
	{ ID id-RIMInformationTransfer	CRITICALITY ignore	TYPE RIMInformationTransfer	PRESENCE optional	},
	...
}
-- **************************************************************
--
-- DOWNLINK RIM INFORMATION TRANSFER
--
-- **************************************************************

DownlinkRIMInformationTransfer ::= SEQUENCE {
	protocolIEs		ProtocolIE-Container		{ {DownlinkRIMInformationTransferIEs} },
	...
}

DownlinkRIMInformationTransferIEs NGAP-PROTOCOL-IES ::= {
	{ ID id-RIMInformationTransfer	CRITICALITY ignore	TYPE RIMInformationTransfer	PRESENCE optional	},

	...
}

-- **************************************************************
--
-- Connection Establishment Indication
--
-- **************************************************************

ConnectionEstablishmentIndication::= SEQUENCE {
	protocolIEs			ProtocolIE-Container { {ConnectionEstablishmentIndicationIEs} },
	...
}

ConnectionEstablishmentIndicationIEs NGAP-PROTOCOL-IES ::= {
	{ ID id-AMF-UE-NGAP-ID					CRITICALITY reject	TYPE AMF-UE-NGAP-ID					PRESENCE mandatory	}|
	{ ID id-RAN-UE-NGAP-ID					CRITICALITY reject	TYPE RAN-UE-NGAP-ID					PRESENCE mandatory	}|
	{ ID id-UERadioCapability				CRITICALITY ignore	TYPE UERadioCapability				PRESENCE optional 	}|
	{ ID id-EndIndication					CRITICALITY ignore	TYPE EndIndication					PRESENCE optional		}|
	{ ID id-S-NSSAI							CRITICALITY ignore	TYPE S-NSSAI						PRESENCE optional		}|
	{ ID id-AllowedNSSAI					CRITICALITY ignore	TYPE AllowedNSSAI					PRESENCE optional		}|
	{ ID id-UE-DifferentiationInfo			CRITICALITY ignore	TYPE UE-DifferentiationInfo			PRESENCE optional		}|
	{ ID id-DL-CP-SecurityInformation		CRITICALITY ignore	TYPE DL-CP-SecurityInformation		PRESENCE optional		}|
	{ ID id-NB-IoT-UEPriority				CRITICALITY ignore	TYPE NB-IoT-UEPriority				PRESENCE optional		}|
	{ ID id-Enhanced-CoverageRestriction	CRITICALITY ignore	TYPE Enhanced-CoverageRestriction	PRESENCE optional		}|
	{ ID id-CEmodeBrestricted				CRITICALITY ignore	TYPE CEmodeBrestricted				PRESENCE optional		}|
	{ ID id-UERadioCapabilityID				CRITICALITY reject	TYPE UERadioCapabilityID			PRESENCE optional		},
	...
}


-- **************************************************************
--
-- UE RADIO CAPABILITY ID MAPPING ELEMENTARY PROCEDURES
--
-- **************************************************************

-- **************************************************************
--
-- UE RADIO CAPABILITY ID MAPPING REQUEST
--
-- **************************************************************

UERadioCapabilityIDMappingRequest ::= SEQUENCE {
	protocolIEs		ProtocolIE-Container		{ {UERadioCapabilityIDMappingRequestIEs} },
	...
}

UERadioCapabilityIDMappingRequestIEs NGAP-PROTOCOL-IES ::= {
	{ ID id-UERadioCapabilityID		CRITICALITY reject	TYPE UERadioCapabilityID	PRESENCE mandatory	},
	...
}

-- **************************************************************
--
-- UE RADIO CAPABILITY ID MAPPING RESPONSE
--
-- **************************************************************

UERadioCapabilityIDMappingResponse ::= SEQUENCE {
	protocolIEs		ProtocolIE-Container		{ {UERadioCapabilityIDMappingResponseIEs} },
	...
}

UERadioCapabilityIDMappingResponseIEs NGAP-PROTOCOL-IES ::= {
	{ ID id-UERadioCapabilityID			CRITICALITY reject	TYPE UERadioCapabilityID		PRESENCE mandatory	}|
	{ ID id-UERadioCapability			CRITICALITY ignore	TYPE UERadioCapability			PRESENCE mandatory 	}|
	{ ID id-CriticalityDiagnostics		CRITICALITY ignore	TYPE CriticalityDiagnostics		PRESENCE optional		},
	...
}

-- **************************************************************
--
-- AMF CP Relocation Indication
--
-- **************************************************************

AMFCPRelocationIndication ::= SEQUENCE {
	protocolIEs			ProtocolIE-Container { { AMFCPRelocationIndicationIEs} },
	...
}

AMFCPRelocationIndicationIEs NGAP-PROTOCOL-IES ::= {
	{ ID id-AMF-UE-NGAP-ID				CRITICALITY reject	TYPE AMF-UE-NGAP-ID				PRESENCE mandatory	}|
	{ ID id-RAN-UE-NGAP-ID				CRITICALITY reject	TYPE RAN-UE-NGAP-ID				PRESENCE mandatory	}|
	{ ID id-S-NSSAI						CRITICALITY ignore	TYPE S-NSSAI					PRESENCE optional		}|
	{ ID id-AllowedNSSAI				CRITICALITY ignore	TYPE AllowedNSSAI				PRESENCE optional		},
	...
}

END
-- ASN1STOP

-- ASN1START
-- **************************************************************
--
-- Information Element Definitions
--
-- **************************************************************

NGAP-IEs {
itu-t (0) identified-organization (4) etsi (0) mobileDomain (0) 
ngran-Access (22) modules (3) ngap (1) version1 (1) ngap-IEs (2) }

DEFINITIONS AUTOMATIC TAGS ::= 

BEGIN

IMPORTS

	id-AdditionalDLForwardingUPTNLInformation,
	id-AdditionalULForwardingUPTNLInformation,
	id-AdditionalDLQosFlowPerTNLInformation,
	id-AdditionalDLUPTNLInformationForHOList,
	id-AdditionalNGU-UP-TNLInformation,
	id-AdditionalRedundantDL-NGU-UP-TNLInformation,
	id-AdditionalRedundantDLQosFlowPerTNLInformation,
	id-AdditionalRedundantNGU-UP-TNLInformation,
	id-AdditionalRedundantUL-NGU-UP-TNLInformation,
	id-AdditionalUL-NGU-UP-TNLInformation,
	id-AlternativeQoSParaSetList,
	id-BurstArrivalTimeDownlink,
	id-Cause,
	id-CNPacketDelayBudgetDL,
	id-CNPacketDelayBudgetUL,
	id-CNTypeRestrictionsForEquivalent,
	id-CNTypeRestrictionsForServing,
	id-CommonNetworkInstance,
	id-ConfiguredTACIndication,
	id-CurrentQoSParaSetIndex,
	id-DAPSRequestInfo,
	id-DAPSResponseInfoList,
	id-DataForwardingNotPossible,
	id-DataForwardingResponseERABList,
	id-DirectForwardingPathAvailability,
	id-DL-NGU-UP-TNLInformation,
	id-EndpointIPAddressAndPort,
	id-ExtendedPacketDelayBudget,
	id-ExtendedRATRestrictionInformation,
	id-ExtendedSliceSupportList,
	id-ExtendedTAISliceSupportList,
	id-ExtendedUEIdentityIndexValue,
	id-GlobalCable-ID,
	id-GlobalRANNodeID,
	id-GlobalTNGF-ID,
 	id-GlobalTWIF-ID,
	id-GlobalW-AGF-ID,
	id-GUAMIType,
	id-LastEUTRAN-PLMNIdentity,
	id-LocationReportingAdditionalInfo,
	id-MaximumIntegrityProtectedDataRate-DL,
	id-MDTConfiguration,
	id-MicoAllPLMN,
	id-NetworkInstance,
	id-NID,
	id-NPN-MobilityInformation,
	id-NPN-PagingAssistanceInformation,
	id-NPN-Support,
	id-OldAssociatedQosFlowList-ULendmarkerexpected,
	id-PagingAssisDataforCEcapabUE,
	id-PagingeDRXInformation,
	id-PDUSessionAggregateMaximumBitRate,
	id-PduSessionExpectedUEActivityBehaviour,
	id-PDUSessionResourceFailedToSetupListCxtFail,
	id-PDUSessionResourceReleaseResponseTransfer,
	id-PDUSessionType,
	id-PSCellInformation,
	id-QosFlowAddOrModifyRequestList,
	id-QosFlowFailedToSetupList,
	id-QosFlowFeedbackList,
	id-QosFlowParametersList,
	id-QosFlowSetupRequestList,
	id-QosFlowToReleaseList,
	id-QosMonitoringRequest,
	id-QosMonitoringReportingFrequency,
	id-RAT-Information,
	id-RedundantCommonNetworkInstance,
	id-RedundantDL-NGU-TNLInformationReused,
	id-RedundantDL-NGU-UP-TNLInformation,
	id-RedundantDLQosFlowPerTNLInformation,
	id-RedundantPDUSessionInformation,
	id-RedundantQosFlowIndicator,
	id-RedundantUL-NGU-UP-TNLInformation,
	id-SCTP-TLAs,
	id-SecondaryRATUsageInformation,
	id-SecurityIndication,
	id-SecurityResult,
	id-SgNB-UE-X2AP-ID,
	id-S-NSSAI,
	id-SONInformationReport,
	id-TNLAssociationTransportLayerAddressNGRAN,
	id-TargetRNC-ID,
	id-TraceCollectionEntityURI,
	id-TSCTrafficCharacteristics,
	id-UEHistoryInformationFromTheUE,
	id-UERadioCapabilityForPaging,
	id-UERadioCapabilityForPagingOfNB-IoT,
	id-UL-NGU-UP-TNLInformation,
	id-UL-NGU-UP-TNLModifyList,
	id-ULForwarding,
	id-ULForwardingUP-TNLInformation,
	id-UsedRSNInformation,
	id-UserLocationInformationTNGF,
	id-UserLocationInformationTWIF,
	id-UserLocationInformationW-AGF,
	maxnoofAllowedAreas,
	maxnoofAllowedCAGsperPLMN,
	maxnoofAllowedS-NSSAIs,
	maxnoofBluetoothName,
	maxnoofBPLMNs,
	maxnoofCAGSperCell,
	maxnoofCandidateCells,
	maxnoofCellIDforMDT,
	maxnoofCellIDforWarning,
	maxnoofCellinAoI,
	maxnoofCellinEAI,
	maxnoofCellsingNB,
	maxnoofCellsinngeNB,
	maxnoofCellinTAI,
	maxnoofCellsinUEHistoryInfo,
	maxnoofCellsUEMovingTrajectory,
	maxnoofDRBs,
	maxnoofEmergencyAreaID,
	maxnoofEAIforRestart,
	maxnoofEPLMNs,
	maxnoofEPLMNsPlusOne,
	maxnoofE-RABs,
	maxnoofErrors,
	maxnoofExtSliceItems,
	maxnoofForbTACs,
	maxnoofFreqforMDT,
	maxnoofMDTPLMNs,
	maxnoofMultiConnectivity,
	maxnoofMultiConnectivityMinusOne,
	maxnoofNeighPCIforMDT,
	maxnoofNGConnectionsToReset,
	maxNRARFCN,
	maxnoofNRCellBands,
	maxnoofPC5QoSFlows,
	maxnoofPDUSessions,
	maxnoofPLMNs,
	maxnoofQosFlows,
	maxnoofQosParaSets,
	maxnoofRANNodeinAoI,
	maxnoofRecommendedCells,
	maxnoofRecommendedRANNodes,
	maxnoofAoI,
	maxnoofSensorName,
	maxnoofServedGUAMIs,
	maxnoofSliceItems,
	maxnoofTACs,
	maxnoofTAforMDT,
	maxnoofTAIforInactive,
	maxnoofTAIforPaging,
	maxnoofTAIforRestart,
	maxnoofTAIforWarning,
	maxnoofTAIinAoI,
	maxnoofTimePeriods,
	maxnoofTNLAssociations,
	maxnoofWLANName,
	maxnoofXnExtTLAs,
	maxnoofXnGTP-TLAs,
	maxnoofXnTLAs

FROM NGAP-Constants

	Criticality,
	ProcedureCode,
	ProtocolIE-ID,
	TriggeringMessage
FROM NGAP-CommonDataTypes

	ProtocolExtensionContainer{},
	ProtocolIE-Container{},
	NGAP-PROTOCOL-EXTENSION,
	ProtocolIE-SingleContainer{},
	NGAP-PROTOCOL-IES
FROM NGAP-Containers;

-- A

AdditionalDLUPTNLInformationForHOList ::= SEQUENCE (SIZE(1..maxnoofMultiConnectivityMinusOne)) OF AdditionalDLUPTNLInformationForHOItem

AdditionalDLUPTNLInformationForHOItem ::= SEQUENCE {
	additionalDL-NGU-UP-TNLInformation				UPTransportLayerInformation,
	additionalQosFlowSetupResponseList				QosFlowListWithDataForwarding,
	additionalDLForwardingUPTNLInformation			UPTransportLayerInformation 							OPTIONAL,
	iE-Extensions		ProtocolExtensionContainer { { AdditionalDLUPTNLInformationForHOItem-ExtIEs} }	OPTIONAL,
	...
}

AdditionalDLUPTNLInformationForHOItem-ExtIEs NGAP-PROTOCOL-EXTENSION ::= {
	{ ID id-AdditionalRedundantDL-NGU-UP-TNLInformation	CRITICALITY ignore	EXTENSION UPTransportLayerInformation		PRESENCE optional		},
	...
}

AdditionalQosFlowInformation ::= ENUMERATED {
	more-likely,
	...
}

AllocationAndRetentionPriority ::= SEQUENCE {
	priorityLevelARP				PriorityLevelARP,
	pre-emptionCapability			Pre-emptionCapability,
	pre-emptionVulnerability		Pre-emptionVulnerability,
	iE-Extensions		ProtocolExtensionContainer { {AllocationAndRetentionPriority-ExtIEs} } OPTIONAL,
	...
}

AllocationAndRetentionPriority-ExtIEs NGAP-PROTOCOL-EXTENSION ::= {
	...
}

Allowed-CAG-List-per-PLMN ::= SEQUENCE (SIZE(1..maxnoofAllowedCAGsperPLMN)) OF CAG-ID

AllowedNSSAI ::= SEQUENCE (SIZE(1..maxnoofAllowedS-NSSAIs)) OF AllowedNSSAI-Item

AllowedNSSAI-Item ::= SEQUENCE {
	s-NSSAI				S-NSSAI,
	iE-Extensions		ProtocolExtensionContainer { {AllowedNSSAI-Item-ExtIEs} } OPTIONAL,
	...
}

AllowedNSSAI-Item-ExtIEs NGAP-PROTOCOL-EXTENSION ::= {
	...
}

Allowed-PNI-NPN-List ::= SEQUENCE (SIZE(1..maxnoofEPLMNsPlusOne)) OF Allowed-PNI-NPN-Item

Allowed-PNI-NPN-Item ::= SEQUENCE {
	pLMNIdentity				PLMNIdentity,
	pNI-NPN-restricted			ENUMERATED {restricted, not-restricted, ...},
	allowed-CAG-List-per-PLMN	Allowed-CAG-List-per-PLMN,
	iE-Extensions			ProtocolExtensionContainer { {Allowed-PNI-NPN-Item-ExtIEs} } OPTIONAL,
	...
}

Allowed-PNI-NPN-Item-ExtIEs NGAP-PROTOCOL-EXTENSION ::= {
	...
}

AllowedTACs ::= SEQUENCE (SIZE(1..maxnoofAllowedAreas)) OF TAC

AlternativeQoSParaSetIndex ::= INTEGER (1..8, ...)

AlternativeQoSParaSetNotifyIndex ::= INTEGER (0..8, ...)

AlternativeQoSParaSetList ::= SEQUENCE (SIZE(1..maxnoofQosParaSets)) OF AlternativeQoSParaSetItem

AlternativeQoSParaSetItem ::= SEQUENCE {
	alternativeQoSParaSetIndex			AlternativeQoSParaSetIndex,
	guaranteedFlowBitRateDL				BitRate												OPTIONAL,
	guaranteedFlowBitRateUL				BitRate												OPTIONAL,
	packetDelayBudget					PacketDelayBudget									OPTIONAL,
	packetErrorRate						PacketErrorRate										OPTIONAL,
	iE-Extensions		ProtocolExtensionContainer { {AlternativeQoSParaSetItem-ExtIEs} }	OPTIONAL,
	...
}

AlternativeQoSParaSetItem-ExtIEs NGAP-PROTOCOL-EXTENSION ::= {
	...
}

AMFName ::= PrintableString (SIZE(1..150, ...))

AMFNameVisibleString ::= VisibleString (SIZE(1..150, ...))

AMFNameUTF8String ::= UTF8String (SIZE(1..150, ...))

AMFPagingTarget ::= CHOICE {
	globalRANNodeID			GlobalRANNodeID,
	tAI						TAI,
	choice-Extensions		ProtocolIE-SingleContainer { {AMFPagingTarget-ExtIEs} }
}

AMFPagingTarget-ExtIEs NGAP-PROTOCOL-IES ::= {
	...
}

AMFPointer ::= BIT STRING (SIZE(6))

AMFRegionID ::= BIT STRING (SIZE(8))

AMFSetID ::= BIT STRING (SIZE(10))

AMF-TNLAssociationSetupList ::= SEQUENCE (SIZE(1..maxnoofTNLAssociations)) OF AMF-TNLAssociationSetupItem

AMF-TNLAssociationSetupItem ::= SEQUENCE {
	aMF-TNLAssociationAddress		CPTransportLayerInformation,
	iE-Extensions		ProtocolExtensionContainer { {AMF-TNLAssociationSetupItem-ExtIEs} }	OPTIONAL,
	...
}

AMF-TNLAssociationSetupItem-ExtIEs NGAP-PROTOCOL-EXTENSION ::= {
	...
}

AMF-TNLAssociationToAddList ::= SEQUENCE (SIZE(1..maxnoofTNLAssociations)) OF AMF-TNLAssociationToAddItem

AMF-TNLAssociationToAddItem ::= SEQUENCE {
	aMF-TNLAssociationAddress		CPTransportLayerInformation,
	tNLAssociationUsage				TNLAssociationUsage										OPTIONAL,
	tNLAddressWeightFactor			TNLAddressWeightFactor,
	iE-Extensions		ProtocolExtensionContainer { {AMF-TNLAssociationToAddItem-ExtIEs} }	OPTIONAL,
	...
}

AMF-TNLAssociationToAddItem-ExtIEs NGAP-PROTOCOL-EXTENSION ::= {
	...
}

AMF-TNLAssociationToRemoveList ::= SEQUENCE (SIZE(1..maxnoofTNLAssociations)) OF AMF-TNLAssociationToRemoveItem

AMF-TNLAssociationToRemoveItem ::= SEQUENCE {
	aMF-TNLAssociationAddress		CPTransportLayerInformation,
	iE-Extensions		ProtocolExtensionContainer { {AMF-TNLAssociationToRemoveItem-ExtIEs} }	OPTIONAL,
	...
}

AMF-TNLAssociationToRemoveItem-ExtIEs NGAP-PROTOCOL-EXTENSION ::= {
	{ID id-TNLAssociationTransportLayerAddressNGRAN	CRITICALITY reject	EXTENSION CPTransportLayerInformation	PRESENCE optional},
	...
}

AMF-TNLAssociationToUpdateList ::= SEQUENCE (SIZE(1..maxnoofTNLAssociations)) OF AMF-TNLAssociationToUpdateItem

AMF-TNLAssociationToUpdateItem ::= SEQUENCE {
	aMF-TNLAssociationAddress		CPTransportLayerInformation,
	tNLAssociationUsage				TNLAssociationUsage											OPTIONAL,
	tNLAddressWeightFactor			TNLAddressWeightFactor										OPTIONAL,
	iE-Extensions		ProtocolExtensionContainer { {AMF-TNLAssociationToUpdateItem-ExtIEs} }	OPTIONAL,
	...
}

AMF-TNLAssociationToUpdateItem-ExtIEs NGAP-PROTOCOL-EXTENSION ::= {
	...
}

AMF-UE-NGAP-ID ::= INTEGER (0..1099511627775)

AreaOfInterest ::= SEQUENCE {
	areaOfInterestTAIList			AreaOfInterestTAIList						OPTIONAL,
	areaOfInterestCellList			AreaOfInterestCellList						OPTIONAL,
 	areaOfInterestRANNodeList		AreaOfInterestRANNodeList					OPTIONAL,
	iE-Extensions		ProtocolExtensionContainer { {AreaOfInterest-ExtIEs} }	OPTIONAL,
	...
}

AreaOfInterest-ExtIEs NGAP-PROTOCOL-EXTENSION ::= {
	...
}

AreaOfInterestCellList ::= SEQUENCE (SIZE(1..maxnoofCellinAoI)) OF AreaOfInterestCellItem

AreaOfInterestCellItem ::= SEQUENCE {
	nGRAN-CGI			NGRAN-CGI,
	iE-Extensions		ProtocolExtensionContainer { {AreaOfInterestCellItem-ExtIEs} }	OPTIONAL,
	...
}

AreaOfInterestCellItem-ExtIEs NGAP-PROTOCOL-EXTENSION ::= {
	...
}

AreaOfInterestList ::= SEQUENCE (SIZE(1..maxnoofAoI)) OF AreaOfInterestItem

AreaOfInterestItem ::= SEQUENCE {
	areaOfInterest						AreaOfInterest,
	locationReportingReferenceID		LocationReportingReferenceID,
	iE-Extensions		ProtocolExtensionContainer { {AreaOfInterestItem-ExtIEs} }	OPTIONAL,
	...
}

AreaOfInterestItem-ExtIEs NGAP-PROTOCOL-EXTENSION ::= {
	...
}

AreaOfInterestRANNodeList ::= SEQUENCE (SIZE(1..maxnoofRANNodeinAoI)) OF AreaOfInterestRANNodeItem

AreaOfInterestRANNodeItem ::= SEQUENCE {
	globalRANNodeID		GlobalRANNodeID,
	iE-Extensions		ProtocolExtensionContainer { {AreaOfInterestRANNodeItem-ExtIEs} }	OPTIONAL,
	...
}

AreaOfInterestRANNodeItem-ExtIEs NGAP-PROTOCOL-EXTENSION ::= {
	...
}

AreaOfInterestTAIList ::= SEQUENCE (SIZE(1..maxnoofTAIinAoI)) OF AreaOfInterestTAIItem

AreaOfInterestTAIItem ::= SEQUENCE {
	tAI					TAI,
	iE-Extensions		ProtocolExtensionContainer { {AreaOfInterestTAIItem-ExtIEs} }	OPTIONAL,
	...
}

AreaOfInterestTAIItem-ExtIEs NGAP-PROTOCOL-EXTENSION ::= {
	...
}

AssistanceDataForPaging ::= SEQUENCE {
	assistanceDataForRecommendedCells		AssistanceDataForRecommendedCells			OPTIONAL,
	pagingAttemptInformation				PagingAttemptInformation					OPTIONAL,
	iE-Extensions		ProtocolExtensionContainer { {AssistanceDataForPaging-ExtIEs} } OPTIONAL,
	...
}

AssistanceDataForPaging-ExtIEs NGAP-PROTOCOL-EXTENSION ::= {
	{ ID id-NPN-PagingAssistanceInformation		CRITICALITY ignore	EXTENSION NPN-PagingAssistanceInformation			PRESENCE optional	}|
	{ ID id-PagingAssisDataforCEcapabUE			CRITICALITY ignore	EXTENSION PagingAssisDataforCEcapabUE				PRESENCE optional	},
	...
}

AssistanceDataForRecommendedCells ::= SEQUENCE {
	recommendedCellsForPaging		RecommendedCellsForPaging, 
	iE-Extensions		ProtocolExtensionContainer { {AssistanceDataForRecommendedCells-ExtIEs} }	OPTIONAL,
	...
}

AssistanceDataForRecommendedCells-ExtIEs NGAP-PROTOCOL-EXTENSION ::= {
	...
}

AssociatedQosFlowList ::= SEQUENCE (SIZE(1..maxnoofQosFlows)) OF AssociatedQosFlowItem

AssociatedQosFlowItem ::= SEQUENCE {
	qosFlowIdentifier				QosFlowIdentifier,
	qosFlowMappingIndication		ENUMERATED {ul, dl, ...}							OPTIONAL,
	iE-Extensions		ProtocolExtensionContainer { {AssociatedQosFlowItem-ExtIEs} }	OPTIONAL,
	...
}

AssociatedQosFlowItem-ExtIEs NGAP-PROTOCOL-EXTENSION ::= {
	{ ID id-CurrentQoSParaSetIndex	CRITICALITY ignore	EXTENSION AlternativeQoSParaSetIndex	PRESENCE optional	},
	...
}

AuthenticatedIndication ::= ENUMERATED {true, ...}

AveragingWindow ::= INTEGER (0..4095, ...)

AreaScopeOfMDT-NR ::= CHOICE {	
	cellBased					CellBasedMDT-NR,
	tABased						TABasedMDT,
	pLMNWide					NULL,
	tAIBased					TAIBasedMDT,
	choice-Extensions		ProtocolIE-SingleContainer { {AreaScopeOfMDT-NR-ExtIEs} }
}

AreaScopeOfMDT-NR-ExtIEs NGAP-PROTOCOL-IES ::= {
	...
}

AreaScopeOfMDT-EUTRA ::= CHOICE {	
	cellBased					CellBasedMDT-EUTRA,
	tABased						TABasedMDT,
	pLMNWide					NULL,
	tAIBased					TAIBasedMDT,
	choice-Extensions		ProtocolIE-SingleContainer { {AreaScopeOfMDT-EUTRA-ExtIEs} }
}

AreaScopeOfMDT-EUTRA-ExtIEs NGAP-PROTOCOL-IES ::= {
	...
}

AreaScopeOfNeighCellsList ::= SEQUENCE (SIZE(1..maxnoofFreqforMDT)) OF AreaScopeOfNeighCellsItem
AreaScopeOfNeighCellsItem ::= SEQUENCE {
	nrFrequencyInfo				NRFrequencyInfo,
	pciListForMDT				PCIListForMDT												OPTIONAL,
	iE-Extensions		ProtocolExtensionContainer { { AreaScopeOfNeighCellsItem-ExtIEs} }	OPTIONAL,
	...
}

AreaScopeOfNeighCellsItem-ExtIEs NGAP-PROTOCOL-EXTENSION ::= {
	...
}

-- B

BitRate	::= INTEGER (0..4000000000000, ...) 

BroadcastCancelledAreaList ::= CHOICE {
	cellIDCancelledEUTRA				CellIDCancelledEUTRA,
	tAICancelledEUTRA					TAICancelledEUTRA,
	emergencyAreaIDCancelledEUTRA		EmergencyAreaIDCancelledEUTRA,
	cellIDCancelledNR					CellIDCancelledNR,
	tAICancelledNR						TAICancelledNR,
	emergencyAreaIDCancelledNR			EmergencyAreaIDCancelledNR,
	choice-Extensions		ProtocolIE-SingleContainer { {BroadcastCancelledAreaList-ExtIEs} }
}

BroadcastCancelledAreaList-ExtIEs NGAP-PROTOCOL-IES ::= {
	...
}

BroadcastCompletedAreaList ::= CHOICE {
	cellIDBroadcastEUTRA				CellIDBroadcastEUTRA,
	tAIBroadcastEUTRA					TAIBroadcastEUTRA,
	emergencyAreaIDBroadcastEUTRA		EmergencyAreaIDBroadcastEUTRA,
	cellIDBroadcastNR					CellIDBroadcastNR,
	tAIBroadcastNR						TAIBroadcastNR,
	emergencyAreaIDBroadcastNR			EmergencyAreaIDBroadcastNR,
	choice-Extensions		ProtocolIE-SingleContainer { {BroadcastCompletedAreaList-ExtIEs} }
}

BroadcastCompletedAreaList-ExtIEs NGAP-PROTOCOL-IES ::= {
	...
}

BroadcastPLMNList ::= SEQUENCE (SIZE(1..maxnoofBPLMNs)) OF BroadcastPLMNItem

BroadcastPLMNItem ::= SEQUENCE {
	pLMNIdentity			PLMNIdentity,
	tAISliceSupportList		SliceSupportList,
	iE-Extensions		ProtocolExtensionContainer { {BroadcastPLMNItem-ExtIEs} } OPTIONAL,
	...
}

BroadcastPLMNItem-ExtIEs NGAP-PROTOCOL-EXTENSION ::= {
	{ID id-NPN-Support	CRITICALITY reject	EXTENSION NPN-Support		PRESENCE optional}|
	{ID id-ExtendedTAISliceSupportList	CRITICALITY reject	EXTENSION ExtendedSliceSupportList 	PRESENCE optional},
	...
}

BluetoothMeasurementConfiguration ::= SEQUENCE {
	bluetoothMeasConfig             BluetoothMeasConfig,
	bluetoothMeasConfigNameList		BluetoothMeasConfigNameList     									OPTIONAL,
	bt-rssi                         ENUMERATED {true, ...}          									OPTIONAL,
	iE-Extensions		ProtocolExtensionContainer { { BluetoothMeasurementConfiguration-ExtIEs } } 	OPTIONAL,
	...
}

BluetoothMeasurementConfiguration-ExtIEs NGAP-PROTOCOL-EXTENSION ::= {
	...
}

BluetoothMeasConfigNameList ::= SEQUENCE (SIZE(1..maxnoofBluetoothName)) OF BluetoothMeasConfigNameItem

BluetoothMeasConfigNameItem ::= SEQUENCE {
	bluetoothName		BluetoothName,
	iE-Extensions		ProtocolExtensionContainer { { BluetoothMeasConfigNameItem-ExtIEs } } 	OPTIONAL,
	...
}

BluetoothMeasConfigNameItem-ExtIEs NGAP-PROTOCOL-EXTENSION ::= {
	...
}

BluetoothMeasConfig::= ENUMERATED {setup,...}

BluetoothName ::= OCTET STRING (SIZE (1..248))

BurstArrivalTime ::= OCTET STRING

-- C

CAG-ID ::= BIT STRING (SIZE(32))

CancelAllWarningMessages ::= ENUMERATED {
	true,
	...
}

CancelledCellsInEAI-EUTRA ::= SEQUENCE (SIZE(1..maxnoofCellinEAI)) OF CancelledCellsInEAI-EUTRA-Item

CancelledCellsInEAI-EUTRA-Item ::= SEQUENCE {
	eUTRA-CGI				EUTRA-CGI,
	numberOfBroadcasts		NumberOfBroadcasts,
	iE-Extensions		ProtocolExtensionContainer { {CancelledCellsInEAI-EUTRA-Item-ExtIEs} } OPTIONAL,
	...
}

CancelledCellsInEAI-EUTRA-Item-ExtIEs NGAP-PROTOCOL-EXTENSION ::= {
	...
}

CancelledCellsInEAI-NR ::= SEQUENCE (SIZE(1..maxnoofCellinEAI)) OF CancelledCellsInEAI-NR-Item

CancelledCellsInEAI-NR-Item ::= SEQUENCE {
	nR-CGI					NR-CGI,
	numberOfBroadcasts		NumberOfBroadcasts,
	iE-Extensions		ProtocolExtensionContainer { {CancelledCellsInEAI-NR-Item-ExtIEs} } OPTIONAL,
	...
}

CancelledCellsInEAI-NR-Item-ExtIEs NGAP-PROTOCOL-EXTENSION ::= {
	...
}

CancelledCellsInTAI-EUTRA ::= SEQUENCE (SIZE(1..maxnoofCellinTAI)) OF CancelledCellsInTAI-EUTRA-Item

CancelledCellsInTAI-EUTRA-Item ::= SEQUENCE {
	eUTRA-CGI				EUTRA-CGI,
	numberOfBroadcasts		NumberOfBroadcasts,
	iE-Extensions		ProtocolExtensionContainer { {CancelledCellsInTAI-EUTRA-Item-ExtIEs} } OPTIONAL,
	...
}

CancelledCellsInTAI-EUTRA-Item-ExtIEs NGAP-PROTOCOL-EXTENSION ::= {
	...
}

CancelledCellsInTAI-NR ::= SEQUENCE (SIZE(1..maxnoofCellinTAI)) OF CancelledCellsInTAI-NR-Item

CancelledCellsInTAI-NR-Item ::= SEQUENCE{
	nR-CGI					NR-CGI,
	numberOfBroadcasts		NumberOfBroadcasts,
	iE-Extensions		ProtocolExtensionContainer { {CancelledCellsInTAI-NR-Item-ExtIEs} } OPTIONAL,
	...
}

CancelledCellsInTAI-NR-Item-ExtIEs NGAP-PROTOCOL-EXTENSION ::= {
	...
}

CandidateCellList ::= SEQUENCE (SIZE(1.. maxnoofCandidateCells)) OF CandidateCellItem

CandidateCellItem ::= SEQUENCE{
	candidateCell		CandidateCell,
	iE-Extensions		ProtocolExtensionContainer { {CandidateCellItem-ExtIEs} } OPTIONAL,
	...
}

CandidateCellItem-ExtIEs NGAP-PROTOCOL-EXTENSION ::= {
	...
}

CandidateCell::= CHOICE {
	candidateCGI			CandidateCellID,
	candidatePCI			CandidatePCI,
	choice-Extensions		ProtocolIE-SingleContainer { { CandidateCell-ExtIEs} }
}

CandidateCell-ExtIEs NGAP-PROTOCOL-IES ::= {
	...
}


CandidateCellID::= SEQUENCE {
	candidateCellID			NR-CGI,
	iE-Extensions			ProtocolExtensionContainer { { CandidateCellID-ExtIEs} }			OPTIONAL,
	...
}

CandidateCellID-ExtIEs NGAP-PROTOCOL-EXTENSION ::= {
	...
}

CandidatePCI::= SEQUENCE {
	candidatePCI			INTEGER (0..1007, ...),
	candidateNRARFCN		INTEGER (0..3279165),
	iE-Extensions			ProtocolExtensionContainer { { CandidatePCI-ExtIEs} }			OPTIONAL,
	...
}

CandidatePCI-ExtIEs NGAP-PROTOCOL-EXTENSION ::= {
	...
}

Cause ::= CHOICE {
	radioNetwork		CauseRadioNetwork,
	transport			CauseTransport,
	nas					CauseNas,
	protocol			CauseProtocol,
	misc				CauseMisc,
	choice-Extensions		ProtocolIE-SingleContainer { {Cause-ExtIEs} }
}

Cause-ExtIEs NGAP-PROTOCOL-IES ::= {
	...
}

CauseMisc ::= ENUMERATED {
	control-processing-overload,
	not-enough-user-plane-processing-resources,
	hardware-failure,
	om-intervention,
	unknown-PLMN-or-SNPN,
	unspecified,
	...
}

CauseNas ::= ENUMERATED {
	normal-release,
	authentication-failure,
	deregister,
	unspecified,
	...
}

CauseProtocol ::= ENUMERATED {
	transfer-syntax-error,
	abstract-syntax-error-reject,
	abstract-syntax-error-ignore-and-notify,
	message-not-compatible-with-receiver-state,
	semantic-error,
	abstract-syntax-error-falsely-constructed-message,
	unspecified,
	...
}

CauseRadioNetwork ::= ENUMERATED {
	unspecified,
	txnrelocoverall-expiry,
	successful-handover,
	release-due-to-ngran-generated-reason,
	release-due-to-5gc-generated-reason,
	handover-cancelled,	
	partial-handover,	
	ho-failure-in-target-5GC-ngran-node-or-target-system,
	ho-target-not-allowed,
	tngrelocoverall-expiry,
	tngrelocprep-expiry,
	cell-not-available,
	unknown-targetID,
	no-radio-resources-available-in-target-cell,
	unknown-local-UE-NGAP-ID,
	inconsistent-remote-UE-NGAP-ID,
	handover-desirable-for-radio-reason,
	time-critical-handover,
	resource-optimisation-handover,
	reduce-load-in-serving-cell,
	user-inactivity,
	radio-connection-with-ue-lost,
	radio-resources-not-available,
	invalid-qos-combination,
	failure-in-radio-interface-procedure,
	interaction-with-other-procedure,
	unknown-PDU-session-ID,
	unkown-qos-flow-ID,
	multiple-PDU-session-ID-instances,
	multiple-qos-flow-ID-instances,
	encryption-and-or-integrity-protection-algorithms-not-supported,
	ng-intra-system-handover-triggered,
	ng-inter-system-handover-triggered,
	xn-handover-triggered,
	not-supported-5QI-value,
	ue-context-transfer,
	ims-voice-eps-fallback-or-rat-fallback-triggered,
	up-integrity-protection-not-possible,
	up-confidentiality-protection-not-possible,
	slice-not-supported,
	ue-in-rrc-inactive-state-not-reachable,
	redirection,
	resources-not-available-for-the-slice,
	ue-max-integrity-protected-data-rate-reason,
	release-due-to-cn-detected-mobility,
	...,
	n26-interface-not-available,
	release-due-to-pre-emption,
	multiple-location-reporting-reference-ID-instances,
	rsn-not-available-for-the-up,
	npn-access-denied,
	cag-only-access-denied,
	insufficient-ue-capabilities
}

CauseTransport ::= ENUMERATED {
	transport-resource-unavailable,
	unspecified,
	...
}

Cell-CAGInformation ::= SEQUENCE {
	nGRAN-CGI				NGRAN-CGI,
	cellCAGList			CellCAGList,
	iE-Extensions		ProtocolExtensionContainer { {Cell-CAGInformation-ExtIEs} } OPTIONAL,
	...
}

Cell-CAGInformation-ExtIEs NGAP-PROTOCOL-EXTENSION ::= {
	...
}


CellCAGList ::= SEQUENCE (SIZE(1..maxnoofCAGSperCell)) OF CAG-ID

CellIDBroadcastEUTRA ::= SEQUENCE (SIZE(1..maxnoofCellIDforWarning)) OF CellIDBroadcastEUTRA-Item

CellIDBroadcastEUTRA-Item ::= SEQUENCE {
	eUTRA-CGI			EUTRA-CGI,
	iE-Extensions		ProtocolExtensionContainer { {CellIDBroadcastEUTRA-Item-ExtIEs} } OPTIONAL,
	...
}

CellIDBroadcastEUTRA-Item-ExtIEs NGAP-PROTOCOL-EXTENSION ::= {
	...
}

CellIDBroadcastNR ::= SEQUENCE (SIZE(1..maxnoofCellIDforWarning)) OF CellIDBroadcastNR-Item

CellIDBroadcastNR-Item ::= SEQUENCE {
	nR-CGI				NR-CGI,
	iE-Extensions		ProtocolExtensionContainer { {CellIDBroadcastNR-Item-ExtIEs} } OPTIONAL,
	...
}

CellIDBroadcastNR-Item-ExtIEs NGAP-PROTOCOL-EXTENSION ::= {
	...
}

CellIDCancelledEUTRA ::= SEQUENCE (SIZE(1..maxnoofCellIDforWarning)) OF CellIDCancelledEUTRA-Item

CellIDCancelledEUTRA-Item ::= SEQUENCE {
	eUTRA-CGI				EUTRA-CGI,
	numberOfBroadcasts		NumberOfBroadcasts,
	iE-Extensions		ProtocolExtensionContainer { {CellIDCancelledEUTRA-Item-ExtIEs} } OPTIONAL,
	...
}

CellIDCancelledEUTRA-Item-ExtIEs NGAP-PROTOCOL-EXTENSION ::= {
	...
}

CellIDCancelledNR ::= SEQUENCE (SIZE(1..maxnoofCellIDforWarning)) OF CellIDCancelledNR-Item

CellIDCancelledNR-Item ::= SEQUENCE {
	nR-CGI					NR-CGI,
	numberOfBroadcasts		NumberOfBroadcasts,
	iE-Extensions		ProtocolExtensionContainer { {CellIDCancelledNR-Item-ExtIEs} } OPTIONAL,
	...
}

CellIDCancelledNR-Item-ExtIEs NGAP-PROTOCOL-EXTENSION ::= {
	...
}

CellIDListForRestart ::= CHOICE {
	eUTRA-CGIListforRestart		EUTRA-CGIList,
	nR-CGIListforRestart		NR-CGIList,
	choice-Extensions		ProtocolIE-SingleContainer { {CellIDListForRestart-ExtIEs} }
}

CellIDListForRestart-ExtIEs NGAP-PROTOCOL-IES ::= {
	...
}

CellSize ::= ENUMERATED {verysmall, small, medium, large, ...}


CellType ::= SEQUENCE {
	cellSize		CellSize,
	iE-Extensions		ProtocolExtensionContainer { {CellType-ExtIEs} }	OPTIONAL,
	...
}

CellType-ExtIEs NGAP-PROTOCOL-EXTENSION ::= {
	...
}

CEmodeBSupport-Indicator ::= ENUMERATED {supported,...}


CEmodeBrestricted ::= ENUMERATED {
	restricted,
	not-restricted,
	...
}

CNAssistedRANTuning ::= SEQUENCE {
	expectedUEBehaviour					ExpectedUEBehaviour							OPTIONAL,
	iE-Extensions		ProtocolExtensionContainer { {CNAssistedRANTuning-ExtIEs} }	OPTIONAL,
	...
}

CNAssistedRANTuning-ExtIEs NGAP-PROTOCOL-EXTENSION ::= {
	...
}

CNTypeRestrictionsForEquivalent ::= SEQUENCE (SIZE(1..maxnoofEPLMNs)) OF CNTypeRestrictionsForEquivalentItem

CNTypeRestrictionsForEquivalentItem ::= SEQUENCE {
	plmnIdentity		PLMNIdentity,
	cn-Type				ENUMERATED {epc-forbidden, fiveGC-forbidden, ...},
	iE-Extensions		ProtocolExtensionContainer { {CNTypeRestrictionsForEquivalentItem-ExtIEs} }		OPTIONAL,
	...
}

CNTypeRestrictionsForEquivalentItem-ExtIEs NGAP-PROTOCOL-EXTENSION ::={
	...
}

CNTypeRestrictionsForServing ::= ENUMERATED {
	epc-forbidden,
	...
}

CommonNetworkInstance ::= OCTET STRING

CompletedCellsInEAI-EUTRA ::= SEQUENCE (SIZE(1..maxnoofCellinEAI)) OF CompletedCellsInEAI-EUTRA-Item

CompletedCellsInEAI-EUTRA-Item ::= SEQUENCE {
	eUTRA-CGI			EUTRA-CGI,
	iE-Extensions		ProtocolExtensionContainer { {CompletedCellsInEAI-EUTRA-Item-ExtIEs} } OPTIONAL,
	...
}

CompletedCellsInEAI-EUTRA-Item-ExtIEs NGAP-PROTOCOL-EXTENSION ::= {
	...
}

CompletedCellsInEAI-NR ::= SEQUENCE (SIZE(1..maxnoofCellinEAI)) OF CompletedCellsInEAI-NR-Item

CompletedCellsInEAI-NR-Item ::= SEQUENCE {
	nR-CGI				NR-CGI,
	iE-Extensions		ProtocolExtensionContainer { {CompletedCellsInEAI-NR-Item-ExtIEs} }	OPTIONAL,
	...
}

CompletedCellsInEAI-NR-Item-ExtIEs NGAP-PROTOCOL-EXTENSION ::= {
	...
}

CompletedCellsInTAI-EUTRA ::= SEQUENCE (SIZE(1..maxnoofCellinTAI)) OF CompletedCellsInTAI-EUTRA-Item

CompletedCellsInTAI-EUTRA-Item ::= SEQUENCE{
	eUTRA-CGI			EUTRA-CGI,
	iE-Extensions		ProtocolExtensionContainer { {CompletedCellsInTAI-EUTRA-Item-ExtIEs} } OPTIONAL,
	...
}

CompletedCellsInTAI-EUTRA-Item-ExtIEs NGAP-PROTOCOL-EXTENSION ::= {
	...
}

CompletedCellsInTAI-NR ::= SEQUENCE (SIZE(1..maxnoofCellinTAI)) OF CompletedCellsInTAI-NR-Item

CompletedCellsInTAI-NR-Item ::= SEQUENCE{
	nR-CGI				NR-CGI,
	iE-Extensions		ProtocolExtensionContainer { {CompletedCellsInTAI-NR-Item-ExtIEs} } OPTIONAL,
	...
}

CompletedCellsInTAI-NR-Item-ExtIEs NGAP-PROTOCOL-EXTENSION ::= {
	...
}

ConcurrentWarningMessageInd ::= ENUMERATED {
	true,
	...
}

ConfidentialityProtectionIndication ::= ENUMERATED {
	required,
	preferred,
	not-needed,
	...
}

ConfidentialityProtectionResult ::= ENUMERATED {
	performed,
	not-performed,
	...
}

ConfiguredTACIndication ::= ENUMERATED {
	true,
	...
}

CoreNetworkAssistanceInformationForInactive ::= SEQUENCE {
	uEIdentityIndexValue				UEIdentityIndexValue,
	uESpecificDRX						PagingDRX																	OPTIONAL,
	periodicRegistrationUpdateTimer		PeriodicRegistrationUpdateTimer,
	mICOModeIndication					MICOModeIndication															OPTIONAL,
	tAIListForInactive					TAIListForInactive,
	expectedUEBehaviour					ExpectedUEBehaviour															OPTIONAL,
	iE-Extensions		ProtocolExtensionContainer { {CoreNetworkAssistanceInformationForInactive-ExtIEs} }	OPTIONAL,
	...
}

CoreNetworkAssistanceInformationForInactive-ExtIEs NGAP-PROTOCOL-EXTENSION ::= {
	{ ID id-PagingeDRXInformation				CRITICALITY ignore	EXTENSION PagingeDRXInformation					PRESENCE optional	}|
	{ ID id-ExtendedUEIdentityIndexValue		CRITICALITY ignore	EXTENSION ExtendedUEIdentityIndexValue			PRESENCE optional	}|
	{ ID id-UERadioCapabilityForPaging			CRITICALITY ignore	EXTENSION UERadioCapabilityForPaging			PRESENCE optional	}|
	{ ID id-MicoAllPLMN							CRITICALITY ignore	EXTENSION MicoAllPLMN								PRESENCE optional	},
	...
}

COUNTValueForPDCP-SN12 ::= SEQUENCE {
	pDCP-SN12			INTEGER (0..4095),
	hFN-PDCP-SN12		INTEGER (0..1048575),
	iE-Extensions		ProtocolExtensionContainer { {COUNTValueForPDCP-SN12-ExtIEs} }	OPTIONAL,
	...
}

COUNTValueForPDCP-SN12-ExtIEs NGAP-PROTOCOL-EXTENSION ::= {
	...
}

COUNTValueForPDCP-SN18 ::= SEQUENCE {
	pDCP-SN18			INTEGER (0..262143),
	hFN-PDCP-SN18		INTEGER (0..16383),
	iE-Extensions		ProtocolExtensionContainer { {COUNTValueForPDCP-SN18-ExtIEs} }	OPTIONAL,
	...
}

COUNTValueForPDCP-SN18-ExtIEs NGAP-PROTOCOL-EXTENSION ::= {
	...
}

CoverageEnhancementLevel ::= OCTET STRING

CPTransportLayerInformation ::= CHOICE {
	endpointIPAddress		TransportLayerAddress,
	choice-Extensions		ProtocolIE-SingleContainer { {CPTransportLayerInformation-ExtIEs} }
}

CPTransportLayerInformation-ExtIEs NGAP-PROTOCOL-IES ::= {
	{ ID id-EndpointIPAddressAndPort		CRITICALITY reject	TYPE EndpointIPAddressAndPort		PRESENCE mandatory	},
	...
}

CriticalityDiagnostics ::= SEQUENCE {
	procedureCode					ProcedureCode											OPTIONAL,
	triggeringMessage				TriggeringMessage										OPTIONAL,
	procedureCriticality			Criticality												OPTIONAL,
	iEsCriticalityDiagnostics		CriticalityDiagnostics-IE-List							OPTIONAL,
	iE-Extensions		ProtocolExtensionContainer {{CriticalityDiagnostics-ExtIEs}}		OPTIONAL,
	...
}

CriticalityDiagnostics-ExtIEs NGAP-PROTOCOL-EXTENSION ::= {
	...
}

CriticalityDiagnostics-IE-List ::= SEQUENCE (SIZE(1..maxnoofErrors)) OF CriticalityDiagnostics-IE-Item

CriticalityDiagnostics-IE-Item ::= SEQUENCE {
	iECriticality		Criticality,
	iE-ID				ProtocolIE-ID,
	typeOfError			TypeOfError,
	iE-Extensions		ProtocolExtensionContainer {{CriticalityDiagnostics-IE-Item-ExtIEs}} OPTIONAL,
	...
}

CriticalityDiagnostics-IE-Item-ExtIEs NGAP-PROTOCOL-EXTENSION ::= {
	...
}

CellBasedMDT-NR::= SEQUENCE {
	cellIdListforMDT	CellIdListforMDT-NR,
	iE-Extensions		ProtocolExtensionContainer { {CellBasedMDT-NR-ExtIEs} } OPTIONAL,
	...
}

CellBasedMDT-NR-ExtIEs NGAP-PROTOCOL-EXTENSION ::= {
	...
}

CellIdListforMDT-NR ::= SEQUENCE (SIZE(1..maxnoofCellIDforMDT)) OF NR-CGI


CellBasedMDT-EUTRA::= SEQUENCE {
	cellIdListforMDT	CellIdListforMDT-EUTRA,
	iE-Extensions		ProtocolExtensionContainer { {CellBasedMDT-EUTRA-ExtIEs} } OPTIONAL,
	...
}

CellBasedMDT-EUTRA-ExtIEs NGAP-PROTOCOL-EXTENSION ::= {
	...
}

CellIdListforMDT-EUTRA ::= SEQUENCE (SIZE(1..maxnoofCellIDforMDT)) OF EUTRA-CGI


-- D

DataCodingScheme ::= BIT STRING (SIZE(8))

DataForwardingAccepted ::= ENUMERATED {
	data-forwarding-accepted,
	...
}

DataForwardingNotPossible ::= ENUMERATED {
	data-forwarding-not-possible,
	...
}

DataForwardingResponseDRBList ::= SEQUENCE (SIZE(1..maxnoofDRBs)) OF DataForwardingResponseDRBItem

DataForwardingResponseDRBItem ::= SEQUENCE {
	dRB-ID								DRB-ID,
	dLForwardingUP-TNLInformation		UPTransportLayerInformation								OPTIONAL,
	uLForwardingUP-TNLInformation		UPTransportLayerInformation								OPTIONAL,
	iE-Extensions		ProtocolExtensionContainer {{DataForwardingResponseDRBItem-ExtIEs}}		OPTIONAL,
	...
}

DataForwardingResponseDRBItem-ExtIEs NGAP-PROTOCOL-EXTENSION ::= {
	...
}

DAPSRequestInfo ::= SEQUENCE {
	dAPSIndicator				ENUMERATED {daps-ho-required, ...},
	iE-Extensions				ProtocolExtensionContainer { {DAPSRequestInfo-ExtIEs} } OPTIONAL,
	...
}

DAPSRequestInfo-ExtIEs NGAP-PROTOCOL-EXTENSION ::= {
	...
}

DAPSResponseInfoList ::= SEQUENCE (SIZE(1.. maxnoofDRBs)) OF DAPSResponseInfoItem

DAPSResponseInfoItem ::= SEQUENCE {
	dRB-ID				DRB-ID,
	dAPSResponseInfo		DAPSResponseInfo,
	iE-Extension			ProtocolExtensionContainer { {DAPSResponseInfoItem-ExtIEs} }		OPTIONAL,
	...
}

DAPSResponseInfoItem-ExtIEs NGAP-PROTOCOL-EXTENSION ::= {
	...
}

DAPSResponseInfo ::= SEQUENCE {
	dapsresponseindicator		ENUMERATED {daps-ho-accepted, daps-ho-not-accepted, ...},
	iE-Extensions			ProtocolExtensionContainer { { DAPSResponseInfo-ExtIEs} } 	OPTIONAL,
	...
}

DAPSResponseInfo-ExtIEs NGAP-PROTOCOL-EXTENSION ::= {
	...
}


DataForwardingResponseERABList ::= SEQUENCE (SIZE(1..maxnoofE-RABs)) OF DataForwardingResponseERABListItem

DataForwardingResponseERABListItem ::= SEQUENCE {
	e-RAB-ID							E-RAB-ID,
	dLForwardingUP-TNLInformation		UPTransportLayerInformation,
	iE-Extensions		ProtocolExtensionContainer { {DataForwardingResponseERABListItem-ExtIEs} }	OPTIONAL,
	...
}

DataForwardingResponseERABListItem-ExtIEs NGAP-PROTOCOL-EXTENSION ::= {
	...
}

DelayCritical ::= ENUMERATED {
	delay-critical,
	non-delay-critical,
	...
}

DL-CP-SecurityInformation ::= SEQUENCE {
	dl-NAS-MAC				DL-NAS-MAC,
	iE-Extensions			ProtocolExtensionContainer { { DL-CP-SecurityInformation-ExtIEs} }	OPTIONAL,
	...
}

DL-CP-SecurityInformation-ExtIEs NGAP-PROTOCOL-EXTENSION ::= {
	...
}

DL-NAS-MAC ::= BIT STRING (SIZE (16))

DLForwarding ::= ENUMERATED {
	dl-forwarding-proposed,
	...
}

DL-NGU-TNLInformationReused ::= ENUMERATED {
	true,
	...
}

DirectForwardingPathAvailability ::= ENUMERATED {
	direct-path-available,
	...
}

DRB-ID ::= INTEGER (1..32, ...)

DRBsSubjectToStatusTransferList ::= SEQUENCE (SIZE(1..maxnoofDRBs)) OF DRBsSubjectToStatusTransferItem

DRBsSubjectToStatusTransferItem ::= SEQUENCE {
	dRB-ID				DRB-ID,
	dRBStatusUL			DRBStatusUL,
	dRBStatusDL			DRBStatusDL,
	iE-Extension		ProtocolExtensionContainer { {DRBsSubjectToStatusTransferItem-ExtIEs} }	OPTIONAL,
	...
}

DRBsSubjectToStatusTransferItem-ExtIEs NGAP-PROTOCOL-EXTENSION ::= {
	{ ID id-OldAssociatedQosFlowList-ULendmarkerexpected	CRITICALITY ignore EXTENSION AssociatedQosFlowList	 PRESENCE optional },
	...
}

DRBStatusDL ::= CHOICE {
	dRBStatusDL12			DRBStatusDL12,
	dRBStatusDL18			DRBStatusDL18,
	choice-Extensions		ProtocolIE-SingleContainer { {DRBStatusDL-ExtIEs} }
}

DRBStatusDL-ExtIEs NGAP-PROTOCOL-IES ::= {
	...
}

DRBStatusDL12 ::= SEQUENCE {
	dL-COUNTValue		COUNTValueForPDCP-SN12,
	iE-Extension		ProtocolExtensionContainer { {DRBStatusDL12-ExtIEs} }		OPTIONAL,
	...
}

DRBStatusDL12-ExtIEs NGAP-PROTOCOL-EXTENSION ::= {
	...
}

DRBStatusDL18 ::= SEQUENCE {
	dL-COUNTValue		COUNTValueForPDCP-SN18,
	iE-Extension		ProtocolExtensionContainer { {DRBStatusDL18-ExtIEs} }		OPTIONAL,
	...
}

DRBStatusDL18-ExtIEs NGAP-PROTOCOL-EXTENSION ::= {
	...
}

DRBStatusUL ::= CHOICE {
	dRBStatusUL12			DRBStatusUL12,
	dRBStatusUL18			DRBStatusUL18,
	choice-Extensions		ProtocolIE-SingleContainer { {DRBStatusUL-ExtIEs} }
}

DRBStatusUL-ExtIEs NGAP-PROTOCOL-IES ::= {
	...
}

DRBStatusUL12 ::= SEQUENCE {
	uL-COUNTValue					COUNTValueForPDCP-SN12,
	receiveStatusOfUL-PDCP-SDUs		BIT STRING (SIZE(1..2048))						OPTIONAL,
	iE-Extension		ProtocolExtensionContainer { {DRBStatusUL12-ExtIEs} }		OPTIONAL,
	...
}

DRBStatusUL12-ExtIEs NGAP-PROTOCOL-EXTENSION ::= {
	...
}

DRBStatusUL18 ::= SEQUENCE {
	uL-COUNTValue					COUNTValueForPDCP-SN18,
	receiveStatusOfUL-PDCP-SDUs		BIT STRING (SIZE(1..131072))					OPTIONAL,
	iE-Extension		ProtocolExtensionContainer { {DRBStatusUL18-ExtIEs} }		OPTIONAL,
	...
}

DRBStatusUL18-ExtIEs NGAP-PROTOCOL-EXTENSION ::= {
	...
}

DRBsToQosFlowsMappingList ::= SEQUENCE (SIZE(1..maxnoofDRBs)) OF DRBsToQosFlowsMappingItem

DRBsToQosFlowsMappingItem ::= SEQUENCE {
	dRB-ID								DRB-ID,
	associatedQosFlowList				AssociatedQosFlowList,
	iE-Extensions		ProtocolExtensionContainer { {DRBsToQosFlowsMappingItem-ExtIEs} }		OPTIONAL,
	...
}

DRBsToQosFlowsMappingItem-ExtIEs NGAP-PROTOCOL-EXTENSION ::= {
	{ ID id-DAPSRequestInfo	CRITICALITY ignore	EXTENSION DAPSRequestInfo	PRESENCE optional  },
	...
}

Dynamic5QIDescriptor ::= SEQUENCE {
	priorityLevelQos			PriorityLevelQos,
	packetDelayBudget			PacketDelayBudget,
	packetErrorRate				PacketErrorRate,
	fiveQI						FiveQI													OPTIONAL,
	delayCritical				DelayCritical											OPTIONAL,
-- The above IE shall be present in case of GBR QoS flow
	averagingWindow				AveragingWindow											OPTIONAL,
-- The above IE shall be present in case of GBR QoS flow
	maximumDataBurstVolume		MaximumDataBurstVolume									OPTIONAL,
	iE-Extensions		ProtocolExtensionContainer { {Dynamic5QIDescriptor-ExtIEs} }	OPTIONAL,
	...
}

Dynamic5QIDescriptor-ExtIEs NGAP-PROTOCOL-EXTENSION ::= {
	{ ID id-ExtendedPacketDelayBudget	CRITICALITY ignore	EXTENSION ExtendedPacketDelayBudget		PRESENCE optional		}|
	{ ID id-CNPacketDelayBudgetDL		CRITICALITY ignore	EXTENSION ExtendedPacketDelayBudget		PRESENCE optional		}|
	{ ID id-CNPacketDelayBudgetUL		CRITICALITY ignore	EXTENSION ExtendedPacketDelayBudget		PRESENCE optional		},
	...
}

-- E

EarlyStatusTransfer-TransparentContainer ::= SEQUENCE {
	procedureStage			ProcedureStageChoice,
	iE-Extensions			ProtocolExtensionContainer { {EarlyStatusTransfer-TransparentContainer-ExtIEs} }	OPTIONAL,
	...
}

EarlyStatusTransfer-TransparentContainer-ExtIEs NGAP-PROTOCOL-EXTENSION ::= {
	...
}

ProcedureStageChoice ::= CHOICE {
	first-dl-count			FirstDLCount,
	choice-Extensions		ProtocolIE-SingleContainer { {ProcedureStageChoice-ExtIEs} }
}

ProcedureStageChoice-ExtIEs NGAP-PROTOCOL-IES ::= {
	...
}

FirstDLCount ::= SEQUENCE {
	dRBsSubjectToEarlyStatusTransfer		DRBsSubjectToEarlyStatusTransfer-List,
	iE-Extension		ProtocolExtensionContainer { {FirstDLCount-ExtIEs} }		OPTIONAL,
	...
}

FirstDLCount-ExtIEs NGAP-PROTOCOL-EXTENSION ::= {
	...
}

DRBsSubjectToEarlyStatusTransfer-List ::= SEQUENCE (SIZE (1.. maxnoofDRBs)) OF DRBsSubjectToEarlyStatusTransfer-Item

DRBsSubjectToEarlyStatusTransfer-Item ::= SEQUENCE {
	dRB-ID				DRB-ID,
	firstDLCOUNT		DRBStatusDL,
	iE-Extension		ProtocolExtensionContainer { { DRBsSubjectToEarlyStatusTransfer-Item-ExtIEs} }	OPTIONAL,
	...
}

DRBsSubjectToEarlyStatusTransfer-Item-ExtIEs NGAP-PROTOCOL-EXTENSION ::= {
	...
}


EDT-Session ::= ENUMERATED {
	true,
	...
}

EmergencyAreaID ::= OCTET STRING (SIZE(3))

EmergencyAreaIDBroadcastEUTRA ::= SEQUENCE (SIZE(1..maxnoofEmergencyAreaID)) OF EmergencyAreaIDBroadcastEUTRA-Item

EmergencyAreaIDBroadcastEUTRA-Item ::= SEQUENCE {
	emergencyAreaID					EmergencyAreaID,
	completedCellsInEAI-EUTRA		CompletedCellsInEAI-EUTRA,
	iE-Extensions		ProtocolExtensionContainer { {EmergencyAreaIDBroadcastEUTRA-Item-ExtIEs} } OPTIONAL,
	...
}

EmergencyAreaIDBroadcastEUTRA-Item-ExtIEs NGAP-PROTOCOL-EXTENSION ::= {
	...
}

EmergencyAreaIDBroadcastNR ::= SEQUENCE (SIZE(1..maxnoofEmergencyAreaID)) OF EmergencyAreaIDBroadcastNR-Item

EmergencyAreaIDBroadcastNR-Item ::= SEQUENCE {
	emergencyAreaID				EmergencyAreaID,
	completedCellsInEAI-NR		CompletedCellsInEAI-NR,
	iE-Extensions		ProtocolExtensionContainer { {EmergencyAreaIDBroadcastNR-Item-ExtIEs} }	OPTIONAL,
	...
}

EmergencyAreaIDBroadcastNR-Item-ExtIEs NGAP-PROTOCOL-EXTENSION ::= {
	...
}

EmergencyAreaIDCancelledEUTRA ::= SEQUENCE (SIZE(1..maxnoofEmergencyAreaID)) OF EmergencyAreaIDCancelledEUTRA-Item

EmergencyAreaIDCancelledEUTRA-Item ::= SEQUENCE {
	emergencyAreaID					EmergencyAreaID,
	cancelledCellsInEAI-EUTRA		CancelledCellsInEAI-EUTRA,
	iE-Extensions		ProtocolExtensionContainer { {EmergencyAreaIDCancelledEUTRA-Item-ExtIEs} } OPTIONAL,
	...
}

EmergencyAreaIDCancelledEUTRA-Item-ExtIEs NGAP-PROTOCOL-EXTENSION ::= {
	...
}

EmergencyAreaIDCancelledNR ::= SEQUENCE (SIZE(1..maxnoofEmergencyAreaID)) OF EmergencyAreaIDCancelledNR-Item

EmergencyAreaIDCancelledNR-Item ::= SEQUENCE {
	emergencyAreaID				EmergencyAreaID,
	cancelledCellsInEAI-NR		CancelledCellsInEAI-NR,
	iE-Extensions		ProtocolExtensionContainer { {EmergencyAreaIDCancelledNR-Item-ExtIEs} }	OPTIONAL,
	...
}

EmergencyAreaIDCancelledNR-Item-ExtIEs NGAP-PROTOCOL-EXTENSION ::= {
	...
}

EmergencyAreaIDList ::= SEQUENCE (SIZE(1..maxnoofEmergencyAreaID)) OF EmergencyAreaID

EmergencyAreaIDListForRestart ::= SEQUENCE (SIZE(1..maxnoofEAIforRestart)) OF EmergencyAreaID

EmergencyFallbackIndicator ::= SEQUENCE {
	emergencyFallbackRequestIndicator		EmergencyFallbackRequestIndicator,
	emergencyServiceTargetCN				EmergencyServiceTargetCN						OPTIONAL,
	iE-Extensions		ProtocolExtensionContainer { {EmergencyFallbackIndicator-ExtIEs} }	OPTIONAL,
	...
}

EmergencyFallbackIndicator-ExtIEs NGAP-PROTOCOL-EXTENSION ::= {
	...
}

EmergencyFallbackRequestIndicator ::= ENUMERATED {
	emergency-fallback-requested,
	...
}

EmergencyServiceTargetCN ::= ENUMERATED {
	fiveGC,
	epc,
	...
}

ENB-ID ::= CHOICE {
	macroENB-ID				BIT STRING (SIZE(20)),
	homeENB-ID				BIT STRING (SIZE(28)),
	short-macroENB-ID 		BIT STRING (SIZE(18)),
	long-macroENB-ID		BIT STRING (SIZE(21)),
	choice-Extensions		ProtocolIE-SingleContainer { { ENB-ID-ExtIEs} }
}

ENB-ID-ExtIEs NGAP-PROTOCOL-IES ::= {
	...
}


Enhanced-CoverageRestriction ::= ENUMERATED {restricted, ... }


Extended-ConnectedTime ::= INTEGER (0..255)

EN-DCSONConfigurationTransfer ::= OCTET STRING

EndpointIPAddressAndPort ::=SEQUENCE {
	endpointIPAddress TransportLayerAddress,
	portNumber			PortNumber,
	iE-Extensions		ProtocolExtensionContainer { { EndpointIPAddressAndPort-ExtIEs} } OPTIONAL
}

EndIndication ::= ENUMERATED {
	no-further-data,
	further-data-exists,
	...
}

EndpointIPAddressAndPort-ExtIEs NGAP-PROTOCOL-EXTENSION ::= {
	...
}

EquivalentPLMNs ::= SEQUENCE (SIZE(1..maxnoofEPLMNs)) OF PLMNIdentity

EPS-TAC ::= OCTET STRING (SIZE(2))

EPS-TAI ::= SEQUENCE {
	pLMNIdentity		PLMNIdentity,
	ePS-TAC				EPS-TAC,
	iE-Extensions		ProtocolExtensionContainer { {EPS-TAI-ExtIEs} } OPTIONAL,
	...
}

EPS-TAI-ExtIEs NGAP-PROTOCOL-EXTENSION ::= {
	...
}

E-RAB-ID ::= INTEGER (0..15, ...)

E-RABInformationList ::= SEQUENCE (SIZE(1..maxnoofE-RABs)) OF E-RABInformationItem

E-RABInformationItem ::= SEQUENCE {
	e-RAB-ID			E-RAB-ID,
	dLForwarding		DLForwarding													OPTIONAL,
	iE-Extensions		ProtocolExtensionContainer { {E-RABInformationItem-ExtIEs} }	OPTIONAL,
	...
}

E-RABInformationItem-ExtIEs NGAP-PROTOCOL-EXTENSION ::= {
	...
}

EUTRACellIdentity ::= BIT STRING (SIZE(28))

EUTRA-CGI ::= SEQUENCE {
	pLMNIdentity			PLMNIdentity,
	eUTRACellIdentity		EUTRACellIdentity,
	iE-Extensions		ProtocolExtensionContainer { {EUTRA-CGI-ExtIEs} } OPTIONAL,
	...
}

EUTRA-CGI-ExtIEs NGAP-PROTOCOL-EXTENSION ::= {
	...
}

EUTRA-CGIList ::= SEQUENCE (SIZE(1..maxnoofCellsinngeNB)) OF EUTRA-CGI

EUTRA-CGIListForWarning ::= SEQUENCE (SIZE(1..maxnoofCellIDforWarning)) OF EUTRA-CGI

EUTRAencryptionAlgorithms ::= BIT STRING (SIZE(16, ...))

EUTRAintegrityProtectionAlgorithms ::= BIT STRING (SIZE(16, ...))

EventType ::= ENUMERATED {
	direct,
	change-of-serve-cell,
	ue-presence-in-area-of-interest,
	stop-change-of-serve-cell,
	stop-ue-presence-in-area-of-interest,
	cancel-location-reporting-for-the-ue,
	...
}

ExpectedActivityPeriod ::= INTEGER (1..30|40|50|60|80|100|120|150|180|181, ...)

ExpectedHOInterval ::= ENUMERATED {
	sec15, sec30, sec60, sec90, sec120, sec180, long-time,
	...
}

ExpectedIdlePeriod ::= INTEGER (1..30|40|50|60|80|100|120|150|180|181, ...)

ExpectedUEActivityBehaviour ::= SEQUENCE {
	expectedActivityPeriod						ExpectedActivityPeriod						OPTIONAL,
	expectedIdlePeriod							ExpectedIdlePeriod							OPTIONAL,
	sourceOfUEActivityBehaviourInformation		SourceOfUEActivityBehaviourInformation		OPTIONAL,
	iE-Extensions		ProtocolExtensionContainer { {ExpectedUEActivityBehaviour-ExtIEs} }	OPTIONAL,
	...
}

ExpectedUEActivityBehaviour-ExtIEs NGAP-PROTOCOL-EXTENSION ::= {
	...
}

ExpectedUEBehaviour ::= SEQUENCE {
	expectedUEActivityBehaviour		ExpectedUEActivityBehaviour 					OPTIONAL,
	expectedHOInterval				ExpectedHOInterval		 						OPTIONAL,
	expectedUEMobility				ExpectedUEMobility								OPTIONAL,
	expectedUEMovingTrajectory		ExpectedUEMovingTrajectory						OPTIONAL,
	iE-Extensions		ProtocolExtensionContainer { {ExpectedUEBehaviour-ExtIEs} }	OPTIONAL,
	...
}

ExpectedUEBehaviour-ExtIEs NGAP-PROTOCOL-EXTENSION ::= {
	...
}

ExpectedUEMobility ::= ENUMERATED {
	stationary,
	mobile,
	...
}

ExpectedUEMovingTrajectory ::= SEQUENCE (SIZE(1..maxnoofCellsUEMovingTrajectory)) OF ExpectedUEMovingTrajectoryItem

ExpectedUEMovingTrajectoryItem ::= SEQUENCE {
	nGRAN-CGI				NGRAN-CGI,
	timeStayedInCell		INTEGER (0..4095)													OPTIONAL,
	iE-Extensions		ProtocolExtensionContainer { {ExpectedUEMovingTrajectoryItem-ExtIEs} }	OPTIONAL,
	...
}

ExpectedUEMovingTrajectoryItem-ExtIEs NGAP-PROTOCOL-EXTENSION ::= {
	...
}

Extended-AMFName	 ::= SEQUENCE {
	aMFNameVisibleString		AMFNameVisibleString				OPTIONAL,
	aMFNameUTF8String			AMFNameUTF8String					OPTIONAL, 
	iE-Extensions				ProtocolExtensionContainer { { Extended-AMFName-ExtIEs } } OPTIONAL,
	...
}

Extended-AMFName-ExtIEs NGAP-PROTOCOL-EXTENSION ::= {
	...
}

ExtendedPacketDelayBudget ::= INTEGER (1..65535, ...)


Extended-RANNodeName	 ::= SEQUENCE {
	rANNodeNameVisibleString		RANNodeNameVisibleString					OPTIONAL,
	rANNodeNameUTF8String			RANNodeNameUTF8String						OPTIONAL, 
	iE-Extensions					ProtocolExtensionContainer { { Extended-RANNodeName-ExtIEs } } OPTIONAL,	...
}

Extended-RANNodeName-ExtIEs NGAP-PROTOCOL-EXTENSION ::= {
	...
}

ExtendedRATRestrictionInformation ::= SEQUENCE {
	primaryRATRestriction		BIT STRING (SIZE(8, ...)),
	secondaryRATRestriction		BIT STRING (SIZE(8, ...)),
	iE-Extensions		ProtocolExtensionContainer { {ExtendedRATRestrictionInformation-ExtIEs} }	OPTIONAL,
	...
}

ExtendedRATRestrictionInformation-ExtIEs NGAP-PROTOCOL-EXTENSION ::= {
	...
}

ExtendedRNC-ID					::= INTEGER (4096..65535)

ExtendedSliceSupportList ::= SEQUENCE (SIZE(1..maxnoofExtSliceItems)) OF SliceSupportItem

ExtendedUEIdentityIndexValue ::= BIT STRING (SIZE(16))

EventTrigger::= CHOICE {
	outOfCoverage				ENUMERATED {true, ...},
	eventL1LoggedMDTConfig		EventL1LoggedMDTConfig,
	choice-Extensions		ProtocolIE-SingleContainer { { EventTrigger-ExtIEs} }
}

EventTrigger-ExtIEs NGAP-PROTOCOL-IES ::= {
	...
}

EventL1LoggedMDTConfig ::= SEQUENCE {
	l1Threshold					MeasurementThresholdL1LoggedMDT,
	hysteresis					Hysteresis,
	timeToTrigger				TimeToTrigger,
	iE-Extensions				ProtocolExtensionContainer { { EventL1LoggedMDTConfig-ExtIEs} } OPTIONAL,
	...
}

EventL1LoggedMDTConfig-ExtIEs NGAP-PROTOCOL-EXTENSION ::= {
	...
}

MeasurementThresholdL1LoggedMDT ::= CHOICE {
	threshold-RSRP				Threshold-RSRP,
	threshold-RSRQ				Threshold-RSRQ,
	choice-Extensions		ProtocolIE-SingleContainer { { MeasurementThresholdL1LoggedMDT-ExtIEs} }
}

MeasurementThresholdL1LoggedMDT-ExtIEs NGAP-PROTOCOL-IES ::= {
	...
}

-- F

FailureIndication ::= SEQUENCE {
	uERLFReportContainer 	UERLFReportContainer,
	iE-Extensions		ProtocolExtensionContainer { { FailureIndication-ExtIEs} }	OPTIONAL,
	...
}

FailureIndication-ExtIEs NGAP-PROTOCOL-EXTENSION ::= {
	...
}

FiveG-S-TMSI ::= SEQUENCE {
	aMFSetID			AMFSetID,
	aMFPointer			AMFPointer,
	fiveG-TMSI			FiveG-TMSI,
	iE-Extensions		ProtocolExtensionContainer { {FiveG-S-TMSI-ExtIEs} }	OPTIONAL,
	...
}

FiveG-S-TMSI-ExtIEs NGAP-PROTOCOL-EXTENSION ::= {
	...
}

FiveG-TMSI ::= OCTET STRING (SIZE(4))

FiveQI ::= INTEGER (0..255, ...)

ForbiddenAreaInformation ::= SEQUENCE (SIZE(1.. maxnoofEPLMNsPlusOne)) OF ForbiddenAreaInformation-Item

ForbiddenAreaInformation-Item ::= SEQUENCE {
	pLMNIdentity		PLMNIdentity,
	forbiddenTACs		ForbiddenTACs,
	iE-Extensions		ProtocolExtensionContainer { {ForbiddenAreaInformation-Item-ExtIEs} } OPTIONAL,
	...
}

ForbiddenAreaInformation-Item-ExtIEs NGAP-PROTOCOL-EXTENSION ::= {
	...
}

ForbiddenTACs ::= SEQUENCE (SIZE(1..maxnoofForbTACs)) OF TAC

FromEUTRANtoNGRAN ::= SEQUENCE {
	sourceeNBID				IntersystemSONeNBID,
	targetNGRANnodeID		IntersystemSONNGRANnodeID,
	iE-Extensions			ProtocolExtensionContainer { { FromEUTRANtoNGRAN-ExtIEs} }			OPTIONAL
}

FromEUTRANtoNGRAN-ExtIEs NGAP-PROTOCOL-EXTENSION ::= {
	...
}

FromNGRANtoEUTRAN ::= SEQUENCE {
	sourceNGRANnodeID		IntersystemSONNGRANnodeID,
	targeteNBID				IntersystemSONeNBID,
	iE-Extensions			ProtocolExtensionContainer { { FromNGRANtoEUTRAN-ExtIEs} }			OPTIONAL
}

FromNGRANtoEUTRAN-ExtIEs NGAP-PROTOCOL-EXTENSION ::= {
	...
}

-- G

GBR-QosInformation ::= SEQUENCE {
	maximumFlowBitRateDL		BitRate,
	maximumFlowBitRateUL		BitRate,
	guaranteedFlowBitRateDL		BitRate,
	guaranteedFlowBitRateUL		BitRate,
	notificationControl			NotificationControl									OPTIONAL,
	maximumPacketLossRateDL		PacketLossRate										OPTIONAL,
	maximumPacketLossRateUL		PacketLossRate										OPTIONAL,
	iE-Extensions		ProtocolExtensionContainer { {GBR-QosInformation-ExtIEs} }	OPTIONAL,
	...
}

GBR-QosInformation-ExtIEs NGAP-PROTOCOL-EXTENSION ::= {
	{ ID id-AlternativeQoSParaSetList	CRITICALITY ignore	EXTENSION AlternativeQoSParaSetList	PRESENCE optional	},
	...
}

GlobalCable-ID ::= OCTET STRING

GlobalENB-ID ::= SEQUENCE {
	pLMNidentity			PLMNIdentity,
	eNB-ID					ENB-ID,
	iE-Extensions			ProtocolExtensionContainer { {GlobalENB-ID-ExtIEs} }		OPTIONAL,
	...
}

GlobalENB-ID-ExtIEs NGAP-PROTOCOL-EXTENSION ::= {
	...
}


GlobalGNB-ID ::= SEQUENCE {
	pLMNIdentity		PLMNIdentity,
	gNB-ID				GNB-ID,
	iE-Extensions		ProtocolExtensionContainer { {GlobalGNB-ID-ExtIEs} } OPTIONAL,
	...
}

GlobalGNB-ID-ExtIEs NGAP-PROTOCOL-EXTENSION ::= {
	...
}

GlobalN3IWF-ID ::= SEQUENCE {
	pLMNIdentity		PLMNIdentity,
	n3IWF-ID			N3IWF-ID,
	iE-Extensions		ProtocolExtensionContainer { {GlobalN3IWF-ID-ExtIEs} } OPTIONAL,
	...
}

GlobalN3IWF-ID-ExtIEs NGAP-PROTOCOL-EXTENSION ::= {
	...
}

GlobalLine-ID ::= SEQUENCE {
	globalLineIdentity		GlobalLineIdentity,
	lineType			LineType									OPTIONAL,
	iE-Extensions		ProtocolExtensionContainer { {GlobalLine-ID-ExtIEs} } 		OPTIONAL,
	...
}

GlobalLine-ID-ExtIEs NGAP-PROTOCOL-EXTENSION ::= {
	...
}

GlobalLineIdentity ::= OCTET STRING

GlobalNgENB-ID ::= SEQUENCE {
	pLMNIdentity		PLMNIdentity,
	ngENB-ID			NgENB-ID,
	iE-Extensions		ProtocolExtensionContainer { {GlobalNgENB-ID-ExtIEs} } OPTIONAL,
	...
}

GlobalNgENB-ID-ExtIEs NGAP-PROTOCOL-EXTENSION ::= {
	...
}

GlobalRANNodeID ::= CHOICE {
	globalGNB-ID			GlobalGNB-ID,
	globalNgENB-ID			GlobalNgENB-ID,
	globalN3IWF-ID			GlobalN3IWF-ID,
	choice-Extensions		ProtocolIE-SingleContainer { {GlobalRANNodeID-ExtIEs} }
}

GlobalRANNodeID-ExtIEs NGAP-PROTOCOL-IES ::= {
	{ ID id-GlobalTNGF-ID		CRITICALITY reject	TYPE GlobalTNGF-ID		PRESENCE mandatory	}|
	{ ID id-GlobalTWIF-ID		CRITICALITY reject	TYPE GlobalTWIF-ID			PRESENCE mandatory 	}|
	{ ID id-GlobalW-AGF-ID		CRITICALITY reject	TYPE GlobalW-AGF-ID			PRESENCE mandatory 	},
	...
}

GlobalTNGF-ID ::= SEQUENCE {
	pLMNIdentity		PLMNIdentity,
	tNGF-ID				TNGF-ID,
	iE-Extensions		ProtocolExtensionContainer { { GlobalTNGF-ID-ExtIEs} } OPTIONAL,
	...
}

GlobalTNGF-ID-ExtIEs NGAP-PROTOCOL-EXTENSION ::= {
	...
}


GlobalTWIF-ID ::= SEQUENCE {
	pLMNIdentity		PLMNIdentity,
	tWIF-ID				TWIF-ID,
	iE-Extensions		ProtocolExtensionContainer { { GlobalTWIF-ID-ExtIEs} } OPTIONAL,
	...
}

GlobalTWIF-ID-ExtIEs NGAP-PROTOCOL-EXTENSION ::= {
	...
}


GlobalW-AGF-ID ::= SEQUENCE {
	pLMNIdentity			PLMNIdentity,
	w-AGF-ID				W-AGF-ID,
	iE-Extensions			ProtocolExtensionContainer { { GlobalW-AGF-ID-ExtIEs} } OPTIONAL,
	...
}

GlobalW-AGF-ID-ExtIEs NGAP-PROTOCOL-EXTENSION ::= {
	...
}

GNB-ID ::= CHOICE {
	gNB-ID		BIT STRING (SIZE(22..32)),
	choice-Extensions		ProtocolIE-SingleContainer { {GNB-ID-ExtIEs} }
}

GNB-ID-ExtIEs NGAP-PROTOCOL-IES ::= {
	...
}

GTP-TEID ::= OCTET STRING (SIZE(4))

GTPTunnel ::= SEQUENCE {
	transportLayerAddress		TransportLayerAddress,
	gTP-TEID					GTP-TEID,
	iE-Extensions		ProtocolExtensionContainer { {GTPTunnel-ExtIEs} } OPTIONAL,
	...
}

GTPTunnel-ExtIEs NGAP-PROTOCOL-EXTENSION ::= {
	...
}

GUAMI ::= SEQUENCE {
	pLMNIdentity		PLMNIdentity,
	aMFRegionID			AMFRegionID,
	aMFSetID			AMFSetID,
	aMFPointer			AMFPointer,
	iE-Extensions		ProtocolExtensionContainer { {GUAMI-ExtIEs} } OPTIONAL,
	...
}

GUAMI-ExtIEs NGAP-PROTOCOL-EXTENSION ::= {
	...
}

GUAMIType ::= ENUMERATED {native, mapped, ...}

-- H

HandoverCommandTransfer ::= SEQUENCE {
	dLForwardingUP-TNLInformation		UPTransportLayerInformation						OPTIONAL,
	qosFlowToBeForwardedList			QosFlowToBeForwardedList						OPTIONAL,
	dataForwardingResponseDRBList		DataForwardingResponseDRBList					OPTIONAL,
	iE-Extensions		ProtocolExtensionContainer { {HandoverCommandTransfer-ExtIEs} } OPTIONAL,
	...
}

HandoverCommandTransfer-ExtIEs NGAP-PROTOCOL-EXTENSION ::= {
	{ ID id-AdditionalDLForwardingUPTNLInformation		CRITICALITY ignore	EXTENSION QosFlowPerTNLInformationList			PRESENCE optional		}|
	{ ID id-ULForwardingUP-TNLInformation				CRITICALITY reject	EXTENSION UPTransportLayerInformation			PRESENCE optional		}|
	{ ID id-AdditionalULForwardingUPTNLInformation		CRITICALITY reject	EXTENSION UPTransportLayerInformationList		PRESENCE optional		}|
	{ ID id-DataForwardingResponseERABList				CRITICALITY ignore	EXTENSION DataForwardingResponseERABList		PRESENCE optional		}|
	{ ID id-QosFlowFailedToSetupList					CRITICALITY ignore	EXTENSION QosFlowListWithCause						PRESENCE optional		},
	...
}

HandoverFlag ::= ENUMERATED {
	handover-preparation,
	...
}

HandoverPreparationUnsuccessfulTransfer ::= SEQUENCE {
	cause				Cause,
	iE-Extensions		ProtocolExtensionContainer { {HandoverPreparationUnsuccessfulTransfer-ExtIEs} }	OPTIONAL,
	...
}

HandoverPreparationUnsuccessfulTransfer-ExtIEs NGAP-PROTOCOL-EXTENSION ::= {
	...
}

HandoverRequestAcknowledgeTransfer ::= SEQUENCE {
	dL-NGU-UP-TNLInformation			UPTransportLayerInformation,
	dLForwardingUP-TNLInformation		UPTransportLayerInformation										OPTIONAL,
	securityResult						SecurityResult													OPTIONAL,
	qosFlowSetupResponseList			QosFlowListWithDataForwarding,
	qosFlowFailedToSetupList			QosFlowListWithCause											OPTIONAL,
	dataForwardingResponseDRBList		DataForwardingResponseDRBList									OPTIONAL,
	iE-Extensions		ProtocolExtensionContainer { {HandoverRequestAcknowledgeTransfer-ExtIEs} }	OPTIONAL,
	...
}

HandoverRequestAcknowledgeTransfer-ExtIEs NGAP-PROTOCOL-EXTENSION ::= {
	{ ID id-AdditionalDLUPTNLInformationForHOList		CRITICALITY ignore	EXTENSION AdditionalDLUPTNLInformationForHOList		PRESENCE optional	}|
	{ ID id-ULForwardingUP-TNLInformation				CRITICALITY reject	EXTENSION UPTransportLayerInformation					PRESENCE optional	}|
	{ ID id-AdditionalULForwardingUPTNLInformation		CRITICALITY reject	EXTENSION UPTransportLayerInformationList				PRESENCE optional	}|
	{ ID id-DataForwardingResponseERABList				CRITICALITY ignore	EXTENSION DataForwardingResponseERABList 				PRESENCE optional	}|
	{ ID id-RedundantDL-NGU-UP-TNLInformation			CRITICALITY ignore	EXTENSION UPTransportLayerInformation 					PRESENCE optional	}|
	{ ID id-UsedRSNInformation							CRITICALITY ignore	EXTENSION RedundantPDUSessionInformation				PRESENCE optional	}|
	{ ID id-GlobalRANNodeID 								CRITICALITY ignore	EXTENSION GlobalRANNodeID									PRESENCE optional	},
	...
}

HandoverRequiredTransfer ::= SEQUENCE {
	directForwardingPathAvailability		DirectForwardingPathAvailability				OPTIONAL,
	iE-Extensions		ProtocolExtensionContainer { {HandoverRequiredTransfer-ExtIEs} }	OPTIONAL,
	...
}

HandoverRequiredTransfer-ExtIEs NGAP-PROTOCOL-EXTENSION ::= {
	...
}

HandoverResourceAllocationUnsuccessfulTransfer ::= SEQUENCE {
	cause						Cause,
	criticalityDiagnostics		CriticalityDiagnostics																	OPTIONAL,
	iE-Extensions		ProtocolExtensionContainer { {HandoverResourceAllocationUnsuccessfulTransfer-ExtIEs} }	OPTIONAL,
	...
}

HandoverResourceAllocationUnsuccessfulTransfer-ExtIEs NGAP-PROTOCOL-EXTENSION ::= {
	...
}

HandoverType ::= ENUMERATED {
	intra5gs,
	fivegs-to-eps,
	eps-to-5gs,
	...,
	fivegs-to-utran
}

HFCNode-ID ::= OCTET STRING

HOReport::= SEQUENCE {
	handoverReportType			ENUMERATED {ho-too-early, ho-to-wrong-cell, intersystem-ping-pong, ...},
	handoverCause				Cause,
	sourcecellCGI				NGRAN-CGI,
	targetcellCGI				NGRAN-CGI,
	reestablishmentcellCGI		NGRAN-CGI									OPTIONAL,
	-- The above IE shall be present if the Handover Report Type IE is set to the value "HO to wrong cell" --
	sourcecellC-RNTI			BIT STRING (SIZE(16))						OPTIONAL,
	targetcellinE-UTRAN			EUTRA-CGI									OPTIONAL,
	-- The above IE shall be present if the Handover Report Type IE is set to the value "Inter System ping-pong" --
	mobilityInformation			MobilityInformation							OPTIONAL,
	uERLFReportContainer		UERLFReportContainer						OPTIONAL,
	iE-Extensions		ProtocolExtensionContainer { { HOReport-ExtIEs} }	OPTIONAL,
	...
}

HOReport-ExtIEs NGAP-PROTOCOL-EXTENSION ::= {
	...
}


Hysteresis ::=                      INTEGER (0..30)

-- I

IAB-Authorized ::= ENUMERATED {
	authorized,
	not-authorized,
	...
}

IAB-Supported ::= ENUMERATED {
	true,
	...
}

IABNodeIndication ::= ENUMERATED {
	true,
	...
}

IMSVoiceSupportIndicator ::= ENUMERATED {
	supported,
	not-supported,
	...
}

IndexToRFSP ::= INTEGER (1..256, ...)

InfoOnRecommendedCellsAndRANNodesForPaging ::= SEQUENCE {
	recommendedCellsForPaging		RecommendedCellsForPaging,
	recommendRANNodesForPaging		RecommendedRANNodesForPaging,
	iE-Extensions		ProtocolExtensionContainer { {InfoOnRecommendedCellsAndRANNodesForPaging-ExtIEs} }	OPTIONAL,
	...
}

InfoOnRecommendedCellsAndRANNodesForPaging-ExtIEs NGAP-PROTOCOL-EXTENSION ::= {
	...
}


IntegrityProtectionIndication ::= ENUMERATED {
	required,
	preferred,
	not-needed,
	...
}

IntegrityProtectionResult ::= ENUMERATED {
	performed,
	not-performed,
	...
}

IntendedNumberOfPagingAttempts ::= INTEGER (1..16, ...)

InterfacesToTrace ::= BIT STRING (SIZE(8))

ImmediateMDTNr ::= SEQUENCE { 
	measurementsToActivate					MeasurementsToActivate,
	m1Configuration							M1Configuration						OPTIONAL, 
-- The above IE shall be present if the Measurements to Activate IE has the first bit set to 1
	m4Configuration							M4Configuration						OPTIONAL, 
-- The above IE shall be present if the Measurements to Activate IE has the third bit set to 1
	m5Configuration							M5Configuration						OPTIONAL,
-- The above IE shall be present if the Measurements to Activate IE has the fourth bit set to 1
	m6Configuration							M6Configuration						OPTIONAL,
-- The above IE shall be present if the Measurements to Activate IE has the fifth bit set to 1
	m7Configuration							M7Configuration						OPTIONAL,
-- The above IE shall be present if the Measurements to Activate IE has the sixth bit set to 1
	bluetoothMeasurementConfiguration		BluetoothMeasurementConfiguration	OPTIONAL,
	wLANMeasurementConfiguration			WLANMeasurementConfiguration 		OPTIONAL,
	mDT-Location-Info 						MDT-Location-Info 					OPTIONAL,
	sensorMeasurementConfiguration			SensorMeasurementConfiguration		OPTIONAL,
	iE-Extensions		ProtocolExtensionContainer { { ImmediateMDTNr-ExtIEs} } OPTIONAL,
	...
}

ImmediateMDTNr-ExtIEs NGAP-PROTOCOL-EXTENSION ::= {
	...
}

InterSystemFailureIndication ::= SEQUENCE {
	uERLFReportContainer		UERLFReportContainer	OPTIONAL,
	iE-Extensions			ProtocolExtensionContainer { { InterSystemFailureIndication-ExtIEs} }			OPTIONAL,
	...
}

InterSystemFailureIndication-ExtIEs NGAP-PROTOCOL-EXTENSION ::= {
	...
}

IntersystemSONConfigurationTransfer ::= SEQUENCE {
	transferType				IntersystemSONTransferType,
	intersystemSONInformation	IntersystemSONInformation,
	iE-Extensions			ProtocolExtensionContainer { { IntersystemSONConfigurationTransfer-ExtIEs} }			OPTIONAL,
	...
}

IntersystemSONConfigurationTransfer-ExtIEs NGAP-PROTOCOL-EXTENSION ::= {
	...
}

IntersystemSONTransferType ::= CHOICE {
	fromEUTRANtoNGRAN				FromEUTRANtoNGRAN,
	fromNGRANtoEUTRAN				FromNGRANtoEUTRAN,
	choice-Extensions		ProtocolIE-SingleContainer { { IntersystemSONTransferType-ExtIEs} }
}
IntersystemSONTransferType-ExtIEs NGAP-PROTOCOL-IES ::= {
	...
}

IntersystemSONeNBID ::= SEQUENCE {
	globaleNBID				GlobalENB-ID,
	selectedEPSTAI			EPS-TAI,
	iE-Extensions			ProtocolExtensionContainer { { IntersystemSONeNBID-ExtIEs} }			OPTIONAL,
	...
}

IntersystemSONeNBID-ExtIEs NGAP-PROTOCOL-EXTENSION ::= {
	...
}

IntersystemSONNGRANnodeID ::= SEQUENCE {
	globalRANNodeID		GlobalRANNodeID,
	selectedTAI			TAI,
	iE-Extensions		ProtocolExtensionContainer { { IntersystemSONNGRANnodeID-ExtIEs} }			OPTIONAL,
	...
}

IntersystemSONNGRANnodeID-ExtIEs NGAP-PROTOCOL-EXTENSION ::= {
	...
}

IntersystemSONInformation ::= CHOICE {
	intersystemSONInformationReport 	IntersystemSONInformationReport,
	choice-Extensions		ProtocolIE-SingleContainer { { IntersystemSONInformation-ExtIEs} }
}

IntersystemSONInformation-ExtIEs NGAP-PROTOCOL-IES ::= {
	...
}

IntersystemSONInformationReport::= CHOICE {
	hOReportInformation				InterSystemHOReport,
	failureIndicationInformation	InterSystemFailureIndication,
	choice-Extensions		ProtocolIE-SingleContainer { { IntersystemSONInformationReport-ExtIEs} }
}

IntersystemSONInformationReport-ExtIEs NGAP-PROTOCOL-IES ::= {
	...
}

InterSystemHOReport ::= SEQUENCE {
	handoverReportType		InterSystemHandoverReportType,
	iE-Extensions			ProtocolExtensionContainer { { InterSystemHOReport-ExtIEs} }			OPTIONAL,
	...
}

InterSystemHOReport-ExtIEs NGAP-PROTOCOL-EXTENSION ::= {
	...
}

InterSystemHandoverReportType ::= CHOICE {
	tooearlyIntersystemHO				TooearlyIntersystemHO,
	intersystemUnnecessaryHO			IntersystemUnnecessaryHO,
	choice-Extensions		ProtocolIE-SingleContainer { { InterSystemHandoverReportType-ExtIEs} }
}

InterSystemHandoverReportType-ExtIEs NGAP-PROTOCOL-IES ::= {
	...
}

IntersystemUnnecessaryHO ::= SEQUENCE {
	sourcecellID			NGRAN-CGI,
	targetcellID			EUTRA-CGI,
	earlyIRATHO				ENUMERATED {true, false, ...},
	candidateCellList		CandidateCellList,
	iE-Extensions			ProtocolExtensionContainer { { IntersystemUnnecessaryHO-ExtIEs} }			OPTIONAL,
	...
}

IntersystemUnnecessaryHO-ExtIEs NGAP-PROTOCOL-EXTENSION ::= {
	...
}

-- J
-- K
-- L

LAC	::= OCTET STRING (SIZE (2))

LAI ::= SEQUENCE {
	pLMNidentity		PLMNIdentity,
	lAC					LAC,
	iE-Extensions		ProtocolExtensionContainer { {LAI-ExtIEs} } OPTIONAL,
	...
}

LAI-ExtIEs NGAP-PROTOCOL-EXTENSION ::= {
	...
}

LastVisitedCellInformation ::= CHOICE {
	nGRANCell		LastVisitedNGRANCellInformation,
	eUTRANCell		LastVisitedEUTRANCellInformation,
	uTRANCell		LastVisitedUTRANCellInformation,
	gERANCell		LastVisitedGERANCellInformation,
	choice-Extensions		ProtocolIE-SingleContainer { {LastVisitedCellInformation-ExtIEs} }
}

LastVisitedCellInformation-ExtIEs NGAP-PROTOCOL-IES ::= {
	...
}

LastVisitedCellItem ::= SEQUENCE {
	lastVisitedCellInformation		LastVisitedCellInformation,
	iE-Extensions		ProtocolExtensionContainer { {LastVisitedCellItem-ExtIEs} }	OPTIONAL,
	...
}

LastVisitedCellItem-ExtIEs NGAP-PROTOCOL-EXTENSION ::= {
	...
}

LastVisitedEUTRANCellInformation ::= OCTET STRING

LastVisitedGERANCellInformation ::= OCTET STRING

LastVisitedNGRANCellInformation::= SEQUENCE {
	globalCellID								NGRAN-CGI,
	cellType									CellType,
	timeUEStayedInCell							TimeUEStayedInCell,
	timeUEStayedInCellEnhancedGranularity		TimeUEStayedInCellEnhancedGranularity 			OPTIONAL,
	hOCauseValue								Cause		 									OPTIONAL,
	iE-Extensions		ProtocolExtensionContainer { {LastVisitedNGRANCellInformation-ExtIEs} }	OPTIONAL,
	...
}

LastVisitedNGRANCellInformation-ExtIEs NGAP-PROTOCOL-EXTENSION ::= {
	...
}

LastVisitedUTRANCellInformation ::= OCTET STRING

LineType ::= ENUMERATED {
	dsl,
	pon,
	...
}


LocationReportingAdditionalInfo ::= ENUMERATED {
	includePSCell,
	...
}

LocationReportingReferenceID ::= INTEGER (1..64, ...)

LocationReportingRequestType ::= SEQUENCE {
	eventType										EventType,
	reportArea										ReportArea,
	areaOfInterestList								AreaOfInterestList								OPTIONAL,
	locationReportingReferenceIDToBeCancelled		LocationReportingReferenceID					OPTIONAL,
-- The above IE shall be present if the event type is set to stop reporting UE presence in the area of interest
	iE-Extensions		ProtocolExtensionContainer { {LocationReportingRequestType-ExtIEs} }		OPTIONAL,
	...
}

LocationReportingRequestType-ExtIEs NGAP-PROTOCOL-EXTENSION ::= {
	{ ID id-LocationReportingAdditionalInfo	CRITICALITY ignore	EXTENSION LocationReportingAdditionalInfo		PRESENCE optional },
	...
}

LoggedMDTNr ::= SEQUENCE {
	loggingInterval						LoggingInterval,
	loggingDuration						LoggingDuration,
	loggedMDTTrigger						LoggedMDTTrigger,
	bluetoothMeasurementConfiguration	BluetoothMeasurementConfiguration	OPTIONAL,
	wLANMeasurementConfiguration		WLANMeasurementConfiguration		OPTIONAL,
	sensorMeasurementConfiguration		SensorMeasurementConfiguration		OPTIONAL,
	areaScopeOfNeighCellsList			AreaScopeOfNeighCellsList			OPTIONAL,
	iE-Extensions		ProtocolExtensionContainer { {LoggedMDTNr-ExtIEs} } OPTIONAL,
	...
}

LoggedMDTNr-ExtIEs	NGAP-PROTOCOL-EXTENSION ::= {
	...
}

LoggingInterval ::= ENUMERATED { 
	ms320, ms640, ms1280, ms2560, ms5120, ms10240, ms20480, ms30720, ms40960, ms61440,
	infinity,
	...
}

LoggingDuration ::= ENUMERATED {m10, m20, m40, m60, m90, m120, ...}

Links-to-log ::= ENUMERATED {
	uplink, 
	downlink, 
	both-uplink-and-downlink, 
	...
}

LoggedMDTTrigger ::= CHOICE{
	periodical			NULL,
	eventTrigger			EventTrigger,
	choice-Extensions		ProtocolIE-SingleContainer { {LoggedMDTTrigger-ExtIEs} }
}

LoggedMDTTrigger-ExtIEs NGAP-PROTOCOL-IES ::= {
	...
}

LTEM-Indication	::= ENUMERATED {lte-m,...}

LTEUERLFReportContainer ::= OCTET STRING

LTEV2XServicesAuthorized ::= SEQUENCE {
	vehicleUE			VehicleUE															OPTIONAL,
	pedestrianUE 		PedestrianUE														OPTIONAL,
	iE-Extensions		ProtocolExtensionContainer { {LTEV2XServicesAuthorized-ExtIEs} }	OPTIONAL,
	...
}

LTEV2XServicesAuthorized-ExtIEs NGAP-PROTOCOL-EXTENSION ::= {
	...
}

LTEUESidelinkAggregateMaximumBitrate ::= SEQUENCE {
	uESidelinkAggregateMaximumBitRate		BitRate,
	iE-Extensions		ProtocolExtensionContainer { {LTEUE-Sidelink-Aggregate-MaximumBitrates-ExtIEs} } OPTIONAL,
	...
}

LTEUE-Sidelink-Aggregate-MaximumBitrates-ExtIEs NGAP-PROTOCOL-EXTENSION ::= {
	...
}

-- M

MaskedIMEISV ::= BIT STRING (SIZE(64))

MaximumDataBurstVolume ::= INTEGER (0..4095, ..., 4096.. 2000000)

MessageIdentifier ::= BIT STRING (SIZE(16))

MaximumIntegrityProtectedDataRate ::= ENUMERATED {
	bitrate64kbs,
	maximum-UE-rate,
	...
}

MicoAllPLMN ::= ENUMERATED {
	true,
	...
}


MICOModeIndication ::= ENUMERATED {
	true,
	...
}

MobilityInformation ::= BIT STRING (SIZE(16))

MobilityRestrictionList ::= SEQUENCE {
	servingPLMN					PLMNIdentity,
	equivalentPLMNs				EquivalentPLMNs											OPTIONAL,
	rATRestrictions				RATRestrictions											OPTIONAL,
	forbiddenAreaInformation	ForbiddenAreaInformation								OPTIONAL, 
	serviceAreaInformation		ServiceAreaInformation									OPTIONAL, 
	iE-Extensions		ProtocolExtensionContainer { {MobilityRestrictionList-ExtIEs} }	OPTIONAL,
	...
}

MobilityRestrictionList-ExtIEs NGAP-PROTOCOL-EXTENSION ::= {
	{ ID id-LastEUTRAN-PLMNIdentity				CRITICALITY ignore	EXTENSION PLMNIdentity								PRESENCE optional		}|
	{ ID id-CNTypeRestrictionsForServing		CRITICALITY ignore	EXTENSION CNTypeRestrictionsForServing			PRESENCE optional		}|
	{ ID id-CNTypeRestrictionsForEquivalent		CRITICALITY ignore	EXTENSION CNTypeRestrictionsForEquivalent		PRESENCE optional		}|
	{ ID id-NPN-MobilityInformation				CRITICALITY reject	EXTENSION NPN-MobilityInformation				PRESENCE optional		},
	...
}

MDTPLMNList ::= SEQUENCE (SIZE(1..maxnoofMDTPLMNs)) OF PLMNIdentity

MDT-Configuration ::= SEQUENCE {
	mdt-Config-NR		MDT-Configuration-NR		OPTIONAL,
	mdt-Config-EUTRA	MDT-Configuration-EUTRA		OPTIONAL,
	iE-Extensions		ProtocolExtensionContainer { { MDT-Configuration-ExtIEs} } OPTIONAL,
	...
}

MDT-Configuration-ExtIEs NGAP-PROTOCOL-EXTENSION ::= {
	...
}

MDT-Configuration-NR ::= SEQUENCE {
	mdt-Activation				MDT-Activation,
	areaScopeOfMDT				AreaScopeOfMDT-NR,
	mDTModeNr					MDTModeNr,
	signallingBasedMDTPLMNList 	MDTPLMNList												OPTIONAL,
	iE-Extensions		ProtocolExtensionContainer { { MDT-Configuration-NR-ExtIEs} } 	OPTIONAL,
	...
}

MDT-Configuration-NR-ExtIEs NGAP-PROTOCOL-EXTENSION ::= {
	...
}

MDT-Configuration-EUTRA ::= SEQUENCE {
	mdt-Activation				MDT-Activation,
	areaScopeOfMDT				AreaScopeOfMDT-EUTRA,
	mDTMode						MDTModeEutra,
	signallingBasedMDTPLMNList 	MDTPLMNList													OPTIONAL,
	iE-Extensions		ProtocolExtensionContainer { { MDT-Configuration-EUTRA-ExtIEs} } 	OPTIONAL,
	...
}

MDT-Configuration-EUTRA-ExtIEs NGAP-PROTOCOL-EXTENSION ::= {
	...
}

MDT-Activation 	::= ENUMERATED { 
	immediate-MDT-only,
	logged-MDT-only,
	immediate-MDT-and-Trace,
	...
}

MDTModeNr ::= CHOICE {
	immediateMDTNr				ImmediateMDTNr,
	loggedMDTNr					LoggedMDTNr,
	choice-Extensions		ProtocolIE-SingleContainer { {MDTModeNr-ExtIEs} }
}

MDTModeNr-ExtIEs NGAP-PROTOCOL-IES ::= {
	...
}

MDTModeEutra ::= OCTET STRING

MeasurementsToActivate ::= BIT STRING(SIZE(8))

M1Configuration ::= SEQUENCE {
	m1reportingTrigger			M1ReportingTrigger,
	m1thresholdEventA2			M1ThresholdEventA2									OPTIONAL,
--	The above IE shall be present if the M1 Reporting Trigger IE is set to A2event-triggered or A2event-triggered periodic
	m1periodicReporting			M1PeriodicReporting									OPTIONAL,
--	The above IE shall be present if the M1 Reporting Trigger IE is set to periodic or A2event-triggered periodic
	iE-Extensions		ProtocolExtensionContainer { { M1Configuration-ExtIEs} } 	OPTIONAL,
	...
}

M1Configuration-ExtIEs NGAP-PROTOCOL-EXTENSION ::= {
	...
}

M1ReportingTrigger ::= ENUMERATED{
	periodic,
	a2eventtriggered,
	a2eventtriggered-periodic,
	...
}

M1ThresholdEventA2 ::= SEQUENCE { 
	m1ThresholdType		M1ThresholdType,
	iE-Extensions		ProtocolExtensionContainer { { M1ThresholdEventA2-ExtIEs} } OPTIONAL,
	...
}

M1ThresholdEventA2-ExtIEs NGAP-PROTOCOL-EXTENSION ::= {
	...
}

M1ThresholdType ::= CHOICE { 
	threshold-RSRP				Threshold-RSRP,
	threshold-RSRQ				Threshold-RSRQ,
	threshold-SINR				Threshold-SINR,
	choice-Extensions		ProtocolIE-SingleContainer { {M1ThresholdType-ExtIEs} }
}

M1ThresholdType-ExtIEs NGAP-PROTOCOL-IES ::= {
	...
}

M1PeriodicReporting ::= SEQUENCE { 
	reportInterval				ReportIntervalMDT,
	reportAmount				ReportAmountMDT,
	iE-Extensions		ProtocolExtensionContainer { { M1PeriodicReporting-ExtIEs} } OPTIONAL,
	...
}

M1PeriodicReporting-ExtIEs NGAP-PROTOCOL-EXTENSION ::= {
	...
}

M4Configuration ::= SEQUENCE {
	m4period			M4period,
	m4-links-to-log		Links-to-log,
	iE-Extensions		ProtocolExtensionContainer { { M4Configuration-ExtIEs} } OPTIONAL,
	...
}

M4Configuration-ExtIEs NGAP-PROTOCOL-EXTENSION ::= {
	...
}

M4period ::= ENUMERATED {ms1024, ms2048, ms5120, ms10240, min1, ... } 

M5Configuration ::= SEQUENCE {
	m5period			M5period,
	m5-links-to-log		Links-to-log,
	iE-Extensions		ProtocolExtensionContainer { { M5Configuration-ExtIEs} } OPTIONAL,
	...
}

M5Configuration-ExtIEs NGAP-PROTOCOL-EXTENSION ::= {
	...
}

M5period ::= ENUMERATED {ms1024, ms2048, ms5120, ms10240, min1, ... } 

M6Configuration ::= SEQUENCE {
	m6report-Interval	M6report-Interval,
	m6-links-to-log		Links-to-log,
	iE-Extensions		ProtocolExtensionContainer { { M6Configuration-ExtIEs} } OPTIONAL,
	...
}

M6Configuration-ExtIEs NGAP-PROTOCOL-EXTENSION ::= {
	...
}

M6report-Interval ::= ENUMERATED { 
	ms120, ms240, ms480, ms640, ms1024, ms2048, ms5120, ms10240, ms20480, ms40960, min1, min6, min12, min30,
	...
}


M7Configuration ::= SEQUENCE {
	m7period			M7period,
	m7-links-to-log		Links-to-log,
	iE-Extensions		ProtocolExtensionContainer { { M7Configuration-ExtIEs} } OPTIONAL,
	...
}

M7Configuration-ExtIEs NGAP-PROTOCOL-EXTENSION ::= {
	...
}

M7period ::= INTEGER(1..60, ...)

MDT-Location-Info ::= SEQUENCE {
	mDT-Location-Information	MDT-Location-Information,
	iE-Extensions		ProtocolExtensionContainer { { MDT-Location-Info-ExtIEs} } OPTIONAL,
	...
}

MDT-Location-Info-ExtIEs NGAP-PROTOCOL-EXTENSION ::= {
	...
}

MDT-Location-Information::= BIT STRING (SIZE (8))

-- N

N3IWF-ID ::= CHOICE {
	n3IWF-ID				BIT STRING (SIZE(16)),
	choice-Extensions		ProtocolIE-SingleContainer { {N3IWF-ID-ExtIEs} }
}

N3IWF-ID-ExtIEs NGAP-PROTOCOL-IES ::= {
	...
}

NAS-PDU ::= OCTET STRING

NASSecurityParametersFromNGRAN ::= OCTET STRING

NB-IoT-DefaultPagingDRX ::= ENUMERATED {
	rf128, rf256, rf512, rf1024, 
	... 
}

NB-IoT-PagingDRX ::= ENUMERATED {
	rf32, rf64, rf128, rf256, rf512, rf1024, 
	... 
}

NB-IoT-Paging-eDRXCycle ::= ENUMERATED {
	hf2, hf4, hf6, hf8, hf10, hf12, hf14, hf16, hf32, hf64, hf128, hf256, hf512, hf1024, 
	...
}

NB-IoT-Paging-TimeWindow ::= ENUMERATED {
	s1, s2, s3, s4, s5, s6, s7, s8, s9, s10, s11, s12, s13, s14, s15, s16, 
	... 
}

NB-IoT-Paging-eDRXInfo ::= SEQUENCE {
	nB-IoT-Paging-eDRXCycle 	NB-IoT-Paging-eDRXCycle,
	nB-IoT-Paging-TimeWindow 	NB-IoT-Paging-TimeWindow 								OPTIONAL,
	iE-Extensions		ProtocolExtensionContainer { { NB-IoT-Paging-eDRXInfo-ExtIEs} } OPTIONAL,
	...
}

NB-IoT-Paging-eDRXInfo-ExtIEs NGAP-PROTOCOL-EXTENSION ::= {
	...
}

NB-IoT-UEPriority ::= INTEGER (0..255, ...)

NetworkInstance ::= INTEGER (1..256, ...)

NewSecurityContextInd ::= ENUMERATED {
	true,
	...
}

NextHopChainingCount ::= INTEGER (0..7)

NextPagingAreaScope ::= ENUMERATED {
	same,
	changed,
	...
}

NgENB-ID ::= CHOICE {
	macroNgENB-ID			BIT STRING (SIZE(20)),
	shortMacroNgENB-ID		BIT STRING (SIZE(18)),
	longMacroNgENB-ID		BIT STRING (SIZE(21)),
	choice-Extensions		ProtocolIE-SingleContainer { {NgENB-ID-ExtIEs} }
}

NgENB-ID-ExtIEs NGAP-PROTOCOL-IES ::= {
	...
}

NotifySourceNGRANNode ::= ENUMERATED {
	notifySource,
	...
}

NGRAN-CGI ::= CHOICE {
	nR-CGI			NR-CGI,
	eUTRA-CGI		EUTRA-CGI,
	choice-Extensions		ProtocolIE-SingleContainer { {NGRAN-CGI-ExtIEs} }
}

NGRAN-CGI-ExtIEs NGAP-PROTOCOL-IES ::= {
	...
}

NGRAN-TNLAssociationToRemoveList ::= SEQUENCE (SIZE(1..maxnoofTNLAssociations)) OF NGRAN-TNLAssociationToRemoveItem

NGRAN-TNLAssociationToRemoveItem::= SEQUENCE {
	tNLAssociationTransportLayerAddress			CPTransportLayerInformation,
	tNLAssociationTransportLayerAddressAMF		CPTransportLayerInformation								OPTIONAL,
	iE-Extensions		ProtocolExtensionContainer { { NGRAN-TNLAssociationToRemoveItem-ExtIEs} } 	OPTIONAL
}

NGRAN-TNLAssociationToRemoveItem-ExtIEs NGAP-PROTOCOL-EXTENSION ::= {
	...
}

NGRANTraceID ::= OCTET STRING (SIZE(8))

NID ::= BIT STRING (SIZE(44))

NonDynamic5QIDescriptor ::= SEQUENCE {
	fiveQI						FiveQI,
	priorityLevelQos			PriorityLevelQos										OPTIONAL,
	averagingWindow				AveragingWindow											OPTIONAL,
	maximumDataBurstVolume		MaximumDataBurstVolume									OPTIONAL,
	iE-Extensions		ProtocolExtensionContainer { {NonDynamic5QIDescriptor-ExtIEs} }	OPTIONAL,
	...
}

NonDynamic5QIDescriptor-ExtIEs NGAP-PROTOCOL-EXTENSION ::= {
	{ ID id-CNPacketDelayBudgetDL	CRITICALITY ignore	EXTENSION ExtendedPacketDelayBudget		PRESENCE optional		}|
	{ ID id-CNPacketDelayBudgetUL	CRITICALITY ignore	EXTENSION ExtendedPacketDelayBudget		PRESENCE optional		},
	...
}

NotAllowedTACs ::= SEQUENCE (SIZE(1..maxnoofAllowedAreas)) OF TAC

NotificationCause ::= ENUMERATED {
	fulfilled,
	not-fulfilled,
	...
}

NotificationControl ::= ENUMERATED {
	notification-requested,
	...
}

NPN-AccessInformation ::= CHOICE {
	pNI-NPN-Access-Information		CellCAGList,
	choice-Extensions				ProtocolIE-SingleContainer { {NPN-AccessInformation-ExtIEs} }
}

NPN-AccessInformation-ExtIEs NGAP-PROTOCOL-IES ::= {
	...
}

NPN-MobilityInformation ::= CHOICE {
	sNPN-MobilityInformation		SNPN-MobilityInformation,
	pNI-NPN-MobilityInformation		PNI-NPN-MobilityInformation,
	choice-Extensions				ProtocolIE-SingleContainer { {NPN-MobilityInformation-ExtIEs} }
}

NPN-MobilityInformation-ExtIEs NGAP-PROTOCOL-IES ::= {
	...
}


NPN-PagingAssistanceInformation ::= CHOICE {
	pNI-NPN-PagingAssistance		Allowed-PNI-NPN-List,
	choice-Extensions				ProtocolIE-SingleContainer { {NPN-PagingAssistanceInformation-ExtIEs} }
}

NPN-PagingAssistanceInformation-ExtIEs NGAP-PROTOCOL-IES ::= {
	...
}

NPN-Support ::= CHOICE {
	sNPN					NID,
	choice-Extensions		ProtocolIE-SingleContainer { {NPN-Support-ExtIEs} }
}

NPN-Support-ExtIEs NGAP-PROTOCOL-IES ::= {
	...
}

NRCellIdentity ::= BIT STRING (SIZE(36))

NR-CGI ::= SEQUENCE {
	pLMNIdentity		PLMNIdentity,
	nRCellIdentity		NRCellIdentity,
	iE-Extensions		ProtocolExtensionContainer { {NR-CGI-ExtIEs} } OPTIONAL,
	...
}

NR-CGI-ExtIEs NGAP-PROTOCOL-EXTENSION ::= {
	...
}

NR-CGIList ::= SEQUENCE (SIZE(1..maxnoofCellsingNB)) OF NR-CGI

NR-CGIListForWarning ::= SEQUENCE (SIZE(1..maxnoofCellIDforWarning)) OF NR-CGI

NRencryptionAlgorithms ::= BIT STRING (SIZE(16, ...))

NRintegrityProtectionAlgorithms ::= BIT STRING (SIZE(16, ...))

NRMobilityHistoryReport ::= OCTET STRING

NRPPa-PDU ::= OCTET STRING

NRUERLFReportContainer ::= OCTET STRING

NumberOfBroadcasts ::= INTEGER (0..65535)

NumberOfBroadcastsRequested ::= INTEGER (0..65535)

NRARFCN	::= INTEGER (0.. maxNRARFCN)

NRFrequencyBand ::= INTEGER (1..1024, ...)

NRFrequencyBand-List ::= SEQUENCE (SIZE(1..maxnoofNRCellBands)) OF NRFrequencyBandItem

NRFrequencyBandItem ::= SEQUENCE {
	nr-frequency-band			NRFrequencyBand,
	iE-Extension		ProtocolExtensionContainer { {NRFrequencyBandItem-ExtIEs} } 	OPTIONAL,
	...
}

NRFrequencyBandItem-ExtIEs NGAP-PROTOCOL-EXTENSION ::= {
	...
}

NRFrequencyInfo ::= SEQUENCE {
	nrARFCN				NRARFCN,
	frequencyBand-List		NRFrequencyBand-List,
	iE-Extension		ProtocolExtensionContainer { {NRFrequencyInfo-ExtIEs} }		OPTIONAL,
	...
}

NRFrequencyInfo-ExtIEs NGAP-PROTOCOL-EXTENSION ::= {
	...
}

NR-PCI ::= INTEGER (0..1007, ...)

NRV2XServicesAuthorized ::= SEQUENCE {
	vehicleUE			VehicleUE														OPTIONAL,
	pedestrianUE 		PedestrianUE													OPTIONAL,
	iE-Extensions		ProtocolExtensionContainer { {NRV2XServicesAuthorized-ExtIEs} }	OPTIONAL,
	...
}

NRV2XServicesAuthorized-ExtIEs NGAP-PROTOCOL-EXTENSION ::= {
	...
}

VehicleUE ::= ENUMERATED { 
	authorized,
	not-authorized,
	...
}

PedestrianUE ::= ENUMERATED { 
	authorized,
	not-authorized,
	...
}

NRUESidelinkAggregateMaximumBitrate ::= SEQUENCE {
	uESidelinkAggregateMaximumBitRate		BitRate,
	iE-Extensions		ProtocolExtensionContainer { {NRUESidelinkAggregateMaximumBitrate-ExtIEs} } OPTIONAL,
	...
}

NRUESidelinkAggregateMaximumBitrate-ExtIEs NGAP-PROTOCOL-EXTENSION ::= {
	...
}

-- O

OverloadAction ::= ENUMERATED {
	reject-non-emergency-mo-dt,
	reject-rrc-cr-signalling,
	permit-emergency-sessions-and-mobile-terminated-services-only,
	permit-high-priority-sessions-and-mobile-terminated-services-only,
	...
}

OverloadResponse ::= CHOICE {
	overloadAction			OverloadAction,
	choice-Extensions		ProtocolIE-SingleContainer { {OverloadResponse-ExtIEs} }
}

OverloadResponse-ExtIEs NGAP-PROTOCOL-IES ::= {
	...
}

OverloadStartNSSAIList ::= SEQUENCE (SIZE (1..maxnoofSliceItems)) OF OverloadStartNSSAIItem

OverloadStartNSSAIItem ::= SEQUENCE {
	sliceOverloadList						SliceOverloadList,
	sliceOverloadResponse					OverloadResponse								OPTIONAL,
	sliceTrafficLoadReductionIndication		TrafficLoadReductionIndication				OPTIONAL,
	iE-Extensions		ProtocolExtensionContainer { {OverloadStartNSSAIItem-ExtIEs} }	OPTIONAL,
	...
}

OverloadStartNSSAIItem-ExtIEs NGAP-PROTOCOL-EXTENSION ::= {
	...
}

-- P

PacketDelayBudget ::= INTEGER (0..1023, ...)

PacketErrorRate ::= SEQUENCE {
	pERScalar		INTEGER (0..9, ...),
	pERExponent		INTEGER (0..9, ...),
	iE-Extensions		ProtocolExtensionContainer { {PacketErrorRate-ExtIEs} }	OPTIONAL,
	...
}

PacketErrorRate-ExtIEs NGAP-PROTOCOL-EXTENSION ::= {
	...
}

PacketLossRate ::= INTEGER (0..1000, ...)

PagingAssisDataforCEcapabUE ::= SEQUENCE {
	eUTRA-CGI							EUTRA-CGI,
	coverageEnhancementLevel			CoverageEnhancementLevel, 
	iE-Extensions						ProtocolExtensionContainer { { PagingAssisDataforCEcapabUE-ExtIEs} } OPTIONAL,
	...
}

PagingAssisDataforCEcapabUE-ExtIEs NGAP-PROTOCOL-EXTENSION ::= {
	...
}

PagingAttemptInformation ::= SEQUENCE {
	pagingAttemptCount					PagingAttemptCount,
	intendedNumberOfPagingAttempts		IntendedNumberOfPagingAttempts,
	nextPagingAreaScope					NextPagingAreaScope									OPTIONAL,
	iE-Extensions		ProtocolExtensionContainer { {PagingAttemptInformation-ExtIEs} }	OPTIONAL,
	...
}

PagingAttemptInformation-ExtIEs NGAP-PROTOCOL-EXTENSION ::= {
	...
}

PagingAttemptCount ::= INTEGER (1..16, ...)

PagingDRX ::= ENUMERATED {
	v32,
	v64,
	v128,
	v256,
	...
}

PagingOrigin ::= ENUMERATED {
	non-3gpp,
	...
}

PagingPriority ::= ENUMERATED {
	priolevel1,
	priolevel2,
	priolevel3,
	priolevel4,
	priolevel5,
	priolevel6,
	priolevel7,
	priolevel8,
	...
}

PagingeDRXInformation ::= SEQUENCE {
	paging-eDRX-Cycle		Paging-eDRX-Cycle,
	paging-Time-Window		Paging-Time-Window											OPTIONAL,
	iE-Extensions		ProtocolExtensionContainer { {PagingeDRXInformation-ExtIEs} }	OPTIONAL,
	...
}

PagingeDRXInformation-ExtIEs NGAP-PROTOCOL-EXTENSION ::= {
	...
}

Paging-eDRX-Cycle ::= ENUMERATED {
	hfhalf, hf1, hf2, hf4, hf6, 
	hf8, hf10, hf12, hf14, hf16, 
	hf32, hf64, hf128, hf256,
	...
}


Paging-Time-Window ::= ENUMERATED {
	s1, s2, s3, s4, s5, 
	s6, s7, s8, s9, s10, 
	s11, s12, s13, s14, s15, s16,
	...
}

PagingProbabilityInformation ::= ENUMERATED {
	p00, p05, p10, p15, p20, p25, p30, p35, p40, p45, p50, p55, p60, p65, p70, p75, p80, p85, p90, p95, p100, 
	...
}

PathSwitchRequestAcknowledgeTransfer ::= SEQUENCE {
	uL-NGU-UP-TNLInformation		UPTransportLayerInformation											OPTIONAL,
	securityIndication				SecurityIndication													OPTIONAL,
	iE-Extensions		ProtocolExtensionContainer { {PathSwitchRequestAcknowledgeTransfer-ExtIEs} }	OPTIONAL,
	...
}

PathSwitchRequestAcknowledgeTransfer-ExtIEs NGAP-PROTOCOL-EXTENSION ::= {
	{ ID id-AdditionalNGU-UP-TNLInformation				CRITICALITY ignore	EXTENSION UPTransportLayerInformationPairList		PRESENCE optional	}|
	{ ID id-RedundantUL-NGU-UP-TNLInformation			CRITICALITY ignore	EXTENSION UPTransportLayerInformation				PRESENCE optional	}|
	{ ID id-AdditionalRedundantNGU-UP-TNLInformation	CRITICALITY ignore	EXTENSION UPTransportLayerInformationPairList		PRESENCE optional	}|
	{ ID id-QosFlowParametersList						CRITICALITY ignore	EXTENSION QosFlowParametersList						PRESENCE optional },
	...
}

PathSwitchRequestSetupFailedTransfer ::= SEQUENCE {
	cause				Cause,
	iE-Extensions		ProtocolExtensionContainer { {PathSwitchRequestSetupFailedTransfer-ExtIEs} }	OPTIONAL,
	...
}

PathSwitchRequestSetupFailedTransfer-ExtIEs NGAP-PROTOCOL-EXTENSION ::= {
	...
}

PathSwitchRequestTransfer ::= SEQUENCE {
	dL-NGU-UP-TNLInformation			UPTransportLayerInformation,
	dL-NGU-TNLInformationReused			DL-NGU-TNLInformationReused							OPTIONAL,
	userPlaneSecurityInformation		UserPlaneSecurityInformation						OPTIONAL,
	qosFlowAcceptedList					QosFlowAcceptedList,
	iE-Extensions		ProtocolExtensionContainer { {PathSwitchRequestTransfer-ExtIEs} }	OPTIONAL,
	...
}

PathSwitchRequestTransfer-ExtIEs NGAP-PROTOCOL-EXTENSION ::= {
	{ ID id-AdditionalDLQosFlowPerTNLInformation				CRITICALITY ignore	EXTENSION QosFlowPerTNLInformationList		PRESENCE optional	}|
	{ ID id-RedundantDL-NGU-UP-TNLInformation					CRITICALITY ignore	EXTENSION UPTransportLayerInformation			PRESENCE optional	}|
	{ ID id-RedundantDL-NGU-TNLInformationReused				CRITICALITY ignore	EXTENSION DL-NGU-TNLInformationReused			PRESENCE optional	}|
	{ ID id-AdditionalRedundantDLQosFlowPerTNLInformation		CRITICALITY ignore	EXTENSION QosFlowPerTNLInformationList		PRESENCE optional	}|
	{ ID id-UsedRSNInformation									CRITICALITY ignore	EXTENSION RedundantPDUSessionInformation		PRESENCE optional	}|
	{ ID id-GlobalRANNodeID 										CRITICALITY ignore	EXTENSION GlobalRANNodeID							PRESENCE optional	},
	...
}

PathSwitchRequestUnsuccessfulTransfer ::= SEQUENCE {
	cause				Cause,
	iE-Extensions		ProtocolExtensionContainer { {PathSwitchRequestUnsuccessfulTransfer-ExtIEs} }	OPTIONAL,
	...
}

PathSwitchRequestUnsuccessfulTransfer-ExtIEs NGAP-PROTOCOL-EXTENSION ::= {
	...
}

PC5QoSParameters ::= SEQUENCE {
	pc5QoSFlowList				PC5QoSFlowList,
	pc5LinkAggregateBitRates	BitRate												OPTIONAL,
	iE-Extensions		ProtocolExtensionContainer { { PC5QoSParameters-ExtIEs} }	OPTIONAL,
	...
}

PC5QoSParameters-ExtIEs NGAP-PROTOCOL-EXTENSION ::= {
             ...
}

PC5QoSFlowList ::= SEQUENCE (SIZE(1..maxnoofPC5QoSFlows)) OF PC5QoSFlowItem

PC5QoSFlowItem::= SEQUENCE {
	pQI					FiveQI,
	pc5FlowBitRates		PC5FlowBitRates											OPTIONAL,
	range				Range													OPTIONAL,
	iE-Extensions		ProtocolExtensionContainer { { PC5QoSFlowItem-ExtIEs} }	OPTIONAL,
	...
}

PC5QoSFlowItem-ExtIEs NGAP-PROTOCOL-EXTENSION ::= {
             ...
}

PC5FlowBitRates ::= SEQUENCE {
	guaranteedFlowBitRate		BitRate,
	maximumFlowBitRate			BitRate,
	iE-Extensions		ProtocolExtensionContainer { { PC5FlowBitRates-ExtIEs} }	OPTIONAL,
	...
}

PC5FlowBitRates-ExtIEs NGAP-PROTOCOL-EXTENSION ::= {
	...
}


PCIListForMDT ::= SEQUENCE (SIZE(1.. maxnoofNeighPCIforMDT)) OF NR-PCI

PrivacyIndicator ::= ENUMERATED {
	immediate-MDT,	
	logged-MDT,	
	...
}

PDUSessionAggregateMaximumBitRate ::= SEQUENCE {
	pDUSessionAggregateMaximumBitRateDL		BitRate,
	pDUSessionAggregateMaximumBitRateUL		BitRate,
	iE-Extensions		ProtocolExtensionContainer { {PDUSessionAggregateMaximumBitRate-ExtIEs} } OPTIONAL,
	...
}

PDUSessionAggregateMaximumBitRate-ExtIEs NGAP-PROTOCOL-EXTENSION ::= {
	...
}

PDUSessionID ::= INTEGER (0..255)

PDUSessionResourceAdmittedList ::= SEQUENCE (SIZE(1..maxnoofPDUSessions)) OF PDUSessionResourceAdmittedItem

PDUSessionResourceAdmittedItem ::= SEQUENCE {
	pDUSessionID							PDUSessionID,
	handoverRequestAcknowledgeTransfer		OCTET STRING (CONTAINING HandoverRequestAcknowledgeTransfer),
	iE-Extensions		ProtocolExtensionContainer { {PDUSessionResourceAdmittedItem-ExtIEs} }	OPTIONAL,
	...
}

PDUSessionResourceAdmittedItem-ExtIEs NGAP-PROTOCOL-EXTENSION ::= {
	...
}

PDUSessionResourceFailedToModifyListModCfm ::= SEQUENCE (SIZE(1..maxnoofPDUSessions)) OF PDUSessionResourceFailedToModifyItemModCfm

PDUSessionResourceFailedToModifyItemModCfm ::= SEQUENCE {
	pDUSessionID												PDUSessionID,
	pDUSessionResourceModifyIndicationUnsuccessfulTransfer		OCTET STRING (CONTAINING PDUSessionResourceModifyIndicationUnsuccessfulTransfer),
	iE-Extensions		ProtocolExtensionContainer { {PDUSessionResourceFailedToModifyItemModCfm-ExtIEs} }	OPTIONAL,
	...
}

PDUSessionResourceFailedToModifyItemModCfm-ExtIEs NGAP-PROTOCOL-EXTENSION ::= {
	...
}

PDUSessionResourceFailedToModifyListModRes ::= SEQUENCE (SIZE(1..maxnoofPDUSessions)) OF PDUSessionResourceFailedToModifyItemModRes

PDUSessionResourceFailedToModifyItemModRes ::= SEQUENCE {
	pDUSessionID										PDUSessionID,
	pDUSessionResourceModifyUnsuccessfulTransfer		OCTET STRING (CONTAINING PDUSessionResourceModifyUnsuccessfulTransfer),
	iE-Extensions		ProtocolExtensionContainer { {PDUSessionResourceFailedToModifyItemModRes-ExtIEs} }	OPTIONAL,
	...
}

PDUSessionResourceFailedToModifyItemModRes-ExtIEs NGAP-PROTOCOL-EXTENSION ::= {
	...
}

PDUSessionResourceFailedToResumeListRESReq ::= SEQUENCE (SIZE(1..maxnoofPDUSessions)) OF PDUSessionResourceFailedToResumeItemRESReq

PDUSessionResourceFailedToResumeItemRESReq ::= SEQUENCE {
	pDUSessionID						PDUSessionID,
	cause								Cause,
	iE-Extensions		ProtocolExtensionContainer { {PDUSessionResourceFailedToResumeItemRESReq-ExtIEs} }	OPTIONAL,
	...
}

PDUSessionResourceFailedToResumeItemRESReq-ExtIEs NGAP-PROTOCOL-EXTENSION ::= {
	...
}


PDUSessionResourceFailedToResumeListRESRes ::= SEQUENCE (SIZE(1..maxnoofPDUSessions)) OF PDUSessionResourceFailedToResumeItemRESRes

PDUSessionResourceFailedToResumeItemRESRes ::= SEQUENCE {
	pDUSessionID						PDUSessionID,
	cause								Cause,
	iE-Extensions		ProtocolExtensionContainer { {PDUSessionResourceFailedToResumeItemRESRes-ExtIEs} }	OPTIONAL,
	...
}

PDUSessionResourceFailedToResumeItemRESRes-ExtIEs NGAP-PROTOCOL-EXTENSION ::= {
	...
}

PDUSessionResourceFailedToSetupListCxtFail ::= SEQUENCE (SIZE(1..maxnoofPDUSessions)) OF PDUSessionResourceFailedToSetupItemCxtFail

PDUSessionResourceFailedToSetupItemCxtFail ::= SEQUENCE {
	pDUSessionID									PDUSessionID,
	pDUSessionResourceSetupUnsuccessfulTransfer		OCTET STRING (CONTAINING PDUSessionResourceSetupUnsuccessfulTransfer),
	iE-Extensions		ProtocolExtensionContainer { {PDUSessionResourceFailedToSetupItemCxtFail-ExtIEs} }	OPTIONAL,
	...
}

PDUSessionResourceFailedToSetupItemCxtFail-ExtIEs NGAP-PROTOCOL-EXTENSION ::= {
	...
}

PDUSessionResourceFailedToSetupListCxtRes ::= SEQUENCE (SIZE(1..maxnoofPDUSessions)) OF PDUSessionResourceFailedToSetupItemCxtRes

PDUSessionResourceFailedToSetupItemCxtRes ::= SEQUENCE {
	pDUSessionID									PDUSessionID,
	pDUSessionResourceSetupUnsuccessfulTransfer		OCTET STRING (CONTAINING PDUSessionResourceSetupUnsuccessfulTransfer),
	iE-Extensions		ProtocolExtensionContainer { {PDUSessionResourceFailedToSetupItemCxtRes-ExtIEs} }	OPTIONAL,
	...
}

PDUSessionResourceFailedToSetupItemCxtRes-ExtIEs NGAP-PROTOCOL-EXTENSION ::= {
	...
}

PDUSessionResourceFailedToSetupListHOAck ::= SEQUENCE (SIZE(1..maxnoofPDUSessions)) OF PDUSessionResourceFailedToSetupItemHOAck

PDUSessionResourceFailedToSetupItemHOAck ::= SEQUENCE {
	pDUSessionID										PDUSessionID,
	handoverResourceAllocationUnsuccessfulTransfer		OCTET STRING (CONTAINING HandoverResourceAllocationUnsuccessfulTransfer),
	iE-Extensions		ProtocolExtensionContainer { {PDUSessionResourceFailedToSetupItemHOAck-ExtIEs} }	OPTIONAL,
	...
}

PDUSessionResourceFailedToSetupItemHOAck-ExtIEs NGAP-PROTOCOL-EXTENSION ::= {
	...
}

PDUSessionResourceFailedToSetupListPSReq ::= SEQUENCE (SIZE(1..maxnoofPDUSessions)) OF PDUSessionResourceFailedToSetupItemPSReq

PDUSessionResourceFailedToSetupItemPSReq ::= SEQUENCE {
	pDUSessionID								PDUSessionID,
	pathSwitchRequestSetupFailedTransfer		OCTET STRING (CONTAINING PathSwitchRequestSetupFailedTransfer),
	iE-Extensions		ProtocolExtensionContainer { {PDUSessionResourceFailedToSetupItemPSReq-ExtIEs} }	OPTIONAL,
	...
}

PDUSessionResourceFailedToSetupItemPSReq-ExtIEs NGAP-PROTOCOL-EXTENSION ::= {
	...
}

PDUSessionResourceFailedToSetupListSURes ::= SEQUENCE (SIZE(1..maxnoofPDUSessions)) OF PDUSessionResourceFailedToSetupItemSURes

PDUSessionResourceFailedToSetupItemSURes ::= SEQUENCE {
	pDUSessionID									PDUSessionID,
	pDUSessionResourceSetupUnsuccessfulTransfer		OCTET STRING (CONTAINING PDUSessionResourceSetupUnsuccessfulTransfer),
	iE-Extensions		ProtocolExtensionContainer { {PDUSessionResourceFailedToSetupItemSURes-ExtIEs} }	OPTIONAL,
	...
}

PDUSessionResourceFailedToSetupItemSURes-ExtIEs NGAP-PROTOCOL-EXTENSION ::= {
	...
}

PDUSessionResourceHandoverList ::= SEQUENCE (SIZE(1..maxnoofPDUSessions)) OF PDUSessionResourceHandoverItem

PDUSessionResourceHandoverItem ::= SEQUENCE {
	pDUSessionID						PDUSessionID,
	handoverCommandTransfer				OCTET STRING (CONTAINING HandoverCommandTransfer),
	iE-Extensions		ProtocolExtensionContainer { {PDUSessionResourceHandoverItem-ExtIEs} }	OPTIONAL,
	...
}

PDUSessionResourceHandoverItem-ExtIEs NGAP-PROTOCOL-EXTENSION ::= {
	...
}

PDUSessionResourceInformationList ::= SEQUENCE (SIZE(1..maxnoofPDUSessions)) OF PDUSessionResourceInformationItem

PDUSessionResourceInformationItem ::= SEQUENCE {
	pDUSessionID					PDUSessionID,
	qosFlowInformationList			QosFlowInformationList,
	dRBsToQosFlowsMappingList		DRBsToQosFlowsMappingList										OPTIONAL,
	iE-Extensions		ProtocolExtensionContainer { {PDUSessionResourceInformationItem-ExtIEs} }	OPTIONAL,
	...
}

PDUSessionResourceInformationItem-ExtIEs NGAP-PROTOCOL-EXTENSION ::= {
	...
}

PDUSessionResourceListCxtRelCpl ::= SEQUENCE (SIZE(1..maxnoofPDUSessions)) OF PDUSessionResourceItemCxtRelCpl

PDUSessionResourceItemCxtRelCpl ::= SEQUENCE {
	pDUSessionID		PDUSessionID,
	iE-Extensions		ProtocolExtensionContainer { {PDUSessionResourceItemCxtRelCpl-ExtIEs} }	OPTIONAL,
	...
}

PDUSessionResourceItemCxtRelCpl-ExtIEs NGAP-PROTOCOL-EXTENSION ::= {
	{ ID id-PDUSessionResourceReleaseResponseTransfer	CRITICALITY ignore	EXTENSION OCTET STRING (CONTAINING PDUSessionResourceReleaseResponseTransfer)	PRESENCE optional	},
	...
}

PDUSessionResourceListCxtRelReq ::= SEQUENCE (SIZE(1..maxnoofPDUSessions)) OF PDUSessionResourceItemCxtRelReq

PDUSessionResourceItemCxtRelReq ::= SEQUENCE {
	pDUSessionID		PDUSessionID,
	iE-Extensions		ProtocolExtensionContainer { {PDUSessionResourceItemCxtRelReq-ExtIEs} }	OPTIONAL,
	...
}

PDUSessionResourceItemCxtRelReq-ExtIEs NGAP-PROTOCOL-EXTENSION ::= {
	...
}

PDUSessionResourceListHORqd ::= SEQUENCE (SIZE(1..maxnoofPDUSessions)) OF PDUSessionResourceItemHORqd

PDUSessionResourceItemHORqd ::= SEQUENCE {
	pDUSessionID							PDUSessionID,
	handoverRequiredTransfer				OCTET STRING (CONTAINING HandoverRequiredTransfer),
	iE-Extensions		ProtocolExtensionContainer { {PDUSessionResourceItemHORqd-ExtIEs} }	OPTIONAL,
	...
}

PDUSessionResourceItemHORqd-ExtIEs NGAP-PROTOCOL-EXTENSION ::= {
	...
}

PDUSessionResourceModifyConfirmTransfer ::= SEQUENCE {
	qosFlowModifyConfirmList			QosFlowModifyConfirmList,
	uLNGU-UP-TNLInformation				UPTransportLayerInformation,
	additionalNG-UUPTNLInformation		UPTransportLayerInformationPairList									OPTIONAL,
	qosFlowFailedToModifyList			QosFlowListWithCause												OPTIONAL,
	iE-Extensions		ProtocolExtensionContainer { {PDUSessionResourceModifyConfirmTransfer-ExtIEs} }	OPTIONAL,
	...
}

PDUSessionResourceModifyConfirmTransfer-ExtIEs NGAP-PROTOCOL-EXTENSION ::= {
	{ ID id-RedundantUL-NGU-UP-TNLInformation			CRITICALITY ignore	EXTENSION UPTransportLayerInformation				PRESENCE optional	}|
	{ ID id-AdditionalRedundantNGU-UP-TNLInformation	CRITICALITY ignore	EXTENSION UPTransportLayerInformationPairList		PRESENCE optional	},
	...
}

PDUSessionResourceModifyIndicationUnsuccessfulTransfer ::= SEQUENCE {
	cause				Cause,
	iE-Extensions		ProtocolExtensionContainer { {PDUSessionResourceModifyIndicationUnsuccessfulTransfer-ExtIEs} }		OPTIONAL,
	...
}

PDUSessionResourceModifyIndicationUnsuccessfulTransfer-ExtIEs NGAP-PROTOCOL-EXTENSION ::= {
	...
}

PDUSessionResourceModifyRequestTransfer ::= SEQUENCE {
	protocolIEs		ProtocolIE-Container		{ {PDUSessionResourceModifyRequestTransferIEs} },
	...
}

PDUSessionResourceModifyRequestTransferIEs NGAP-PROTOCOL-IES ::= {
	{ ID id-PDUSessionAggregateMaximumBitRate			CRITICALITY reject	TYPE PDUSessionAggregateMaximumBitRate		PRESENCE	optional		}|
	{ ID id-UL-NGU-UP-TNLModifyList						CRITICALITY reject	TYPE UL-NGU-UP-TNLModifyList					PRESENCE	optional		}|
	{ ID id-NetworkInstance								CRITICALITY reject	TYPE NetworkInstance								PRESENCE optional		}|
	{ ID id-QosFlowAddOrModifyRequestList				CRITICALITY reject	TYPE QosFlowAddOrModifyRequestList			PRESENCE optional		}|
	{ ID id-QosFlowToReleaseList						CRITICALITY reject	TYPE QosFlowListWithCause						PRESENCE optional		}|
	{ ID id-AdditionalUL-NGU-UP-TNLInformation			CRITICALITY reject	TYPE UPTransportLayerInformationList			PRESENCE optional		}|
	{ ID id-CommonNetworkInstance						CRITICALITY ignore	TYPE CommonNetworkInstance						PRESENCE optional		}|
	{ ID id-AdditionalRedundantUL-NGU-UP-TNLInformation	CRITICALITY ignore	TYPE UPTransportLayerInformationList			PRESENCE optional		}|
	{ ID id-RedundantCommonNetworkInstance				CRITICALITY ignore	TYPE CommonNetworkInstance						PRESENCE optional		}|
	{ ID id-RedundantUL-NGU-UP-TNLInformation			CRITICALITY ignore	TYPE UPTransportLayerInformation				PRESENCE optional	 	}|
	{ ID id-SecurityIndication							CRITICALITY ignore	TYPE SecurityIndication							PRESENCE optional		},
	...
}	

PDUSessionResourceModifyResponseTransfer ::= SEQUENCE {
	dL-NGU-UP-TNLInformation				UPTransportLayerInformation											OPTIONAL,
	uL-NGU-UP-TNLInformation				UPTransportLayerInformation											OPTIONAL,
	qosFlowAddOrModifyResponseList			QosFlowAddOrModifyResponseList										OPTIONAL,
	additionalDLQosFlowPerTNLInformation	QosFlowPerTNLInformationList										OPTIONAL,
	qosFlowFailedToAddOrModifyList			QosFlowListWithCause												OPTIONAL,
	iE-Extensions		ProtocolExtensionContainer { {PDUSessionResourceModifyResponseTransfer-ExtIEs} }	OPTIONAL,
	...
}

PDUSessionResourceModifyResponseTransfer-ExtIEs NGAP-PROTOCOL-EXTENSION ::= {
	{ ID id-AdditionalNGU-UP-TNLInformation					CRITICALITY ignore	EXTENSION UPTransportLayerInformationPairList	PRESENCE optional	}|
	{ ID id-RedundantDL-NGU-UP-TNLInformation				CRITICALITY ignore	EXTENSION UPTransportLayerInformation				PRESENCE optional	}|
	{ ID id-RedundantUL-NGU-UP-TNLInformation				CRITICALITY ignore	EXTENSION UPTransportLayerInformation				PRESENCE optional	}|
	{ ID id-AdditionalRedundantDLQosFlowPerTNLInformation	CRITICALITY ignore	EXTENSION QosFlowPerTNLInformationList				PRESENCE optional	}|
	{ ID id-AdditionalRedundantNGU-UP-TNLInformation		CRITICALITY ignore	EXTENSION UPTransportLayerInformationPairList	PRESENCE optional	},
	...
}

PDUSessionResourceModifyIndicationTransfer ::= SEQUENCE {
	dLQosFlowPerTNLInformation					QosFlowPerTNLInformation,
	additionalDLQosFlowPerTNLInformation		QosFlowPerTNLInformationList 									OPTIONAL,
	iE-Extensions		ProtocolExtensionContainer { {PDUSessionResourceModifyIndicationTransfer-ExtIEs} }	OPTIONAL,
	...
}

PDUSessionResourceModifyIndicationTransfer-ExtIEs NGAP-PROTOCOL-EXTENSION ::= {
	{ ID id-SecondaryRATUsageInformation					CRITICALITY ignore	EXTENSION SecondaryRATUsageInformation		PRESENCE optional	}|
	{ ID id-SecurityResult									CRITICALITY ignore	EXTENSION SecurityResult						PRESENCE optional	}|
	{ ID id-RedundantDLQosFlowPerTNLInformation				CRITICALITY ignore	EXTENSION QosFlowPerTNLInformation			PRESENCE optional	}|
	{ ID id-AdditionalRedundantDLQosFlowPerTNLInformation	CRITICALITY ignore	EXTENSION QosFlowPerTNLInformationList		PRESENCE optional	}|
	{ ID id-GlobalRANNodeID 								CRITICALITY ignore	EXTENSION GlobalRANNodeID						PRESENCE optional	},
	...
}

PDUSessionResourceModifyListModCfm ::= SEQUENCE (SIZE(1..maxnoofPDUSessions)) OF PDUSessionResourceModifyItemModCfm

PDUSessionResourceModifyItemModCfm ::= SEQUENCE {
	pDUSessionID								PDUSessionID,
	pDUSessionResourceModifyConfirmTransfer		OCTET STRING (CONTAINING PDUSessionResourceModifyConfirmTransfer),
	iE-Extensions		ProtocolExtensionContainer { {PDUSessionResourceModifyItemModCfm-ExtIEs} }	OPTIONAL,
	...
}

PDUSessionResourceModifyItemModCfm-ExtIEs NGAP-PROTOCOL-EXTENSION ::= {
	...
}

PDUSessionResourceModifyListModInd ::= SEQUENCE (SIZE(1..maxnoofPDUSessions)) OF PDUSessionResourceModifyItemModInd

PDUSessionResourceModifyItemModInd ::= SEQUENCE {
	pDUSessionID									PDUSessionID,
	pDUSessionResourceModifyIndicationTransfer		OCTET STRING (CONTAINING PDUSessionResourceModifyIndicationTransfer),
	iE-Extensions		ProtocolExtensionContainer { {PDUSessionResourceModifyItemModInd-ExtIEs} }	OPTIONAL,
	...
}

PDUSessionResourceModifyItemModInd-ExtIEs NGAP-PROTOCOL-EXTENSION ::= {
	...
}

PDUSessionResourceModifyListModReq ::= SEQUENCE (SIZE(1..maxnoofPDUSessions)) OF PDUSessionResourceModifyItemModReq

PDUSessionResourceModifyItemModReq ::= SEQUENCE {
	pDUSessionID								PDUSessionID,
	nAS-PDU										NAS-PDU													OPTIONAL,
	pDUSessionResourceModifyRequestTransfer		OCTET STRING (CONTAINING PDUSessionResourceModifyRequestTransfer),
	iE-Extensions		ProtocolExtensionContainer { {PDUSessionResourceModifyItemModReq-ExtIEs} }	OPTIONAL,
	...
}

PDUSessionResourceModifyItemModReq-ExtIEs NGAP-PROTOCOL-EXTENSION ::= {
	{ ID id-S-NSSAI											CRITICALITY reject	EXTENSION S-NSSAI						PRESENCE optional	}|
	{ ID id-PduSessionExpectedUEActivityBehaviour			CRITICALITY ignore	EXTENSION ExpectedUEActivityBehaviour	PRESENCE optional	},
	...
}

PDUSessionResourceModifyListModRes ::= SEQUENCE (SIZE(1..maxnoofPDUSessions)) OF PDUSessionResourceModifyItemModRes

PDUSessionResourceModifyItemModRes ::= SEQUENCE {
	pDUSessionID									PDUSessionID,
	pDUSessionResourceModifyResponseTransfer		OCTET STRING (CONTAINING PDUSessionResourceModifyResponseTransfer),
	iE-Extensions		ProtocolExtensionContainer { {PDUSessionResourceModifyItemModRes-ExtIEs} }	OPTIONAL,
	...
}

PDUSessionResourceModifyItemModRes-ExtIEs NGAP-PROTOCOL-EXTENSION ::= {
	...
}

PDUSessionResourceModifyUnsuccessfulTransfer ::= SEQUENCE {
	cause						Cause,
	criticalityDiagnostics		CriticalityDiagnostics																OPTIONAL,
	iE-Extensions		ProtocolExtensionContainer { {PDUSessionResourceModifyUnsuccessfulTransfer-ExtIEs} }	OPTIONAL,
	...
}

PDUSessionResourceModifyUnsuccessfulTransfer-ExtIEs NGAP-PROTOCOL-EXTENSION ::= {
	...
}

PDUSessionResourceNotifyList ::= SEQUENCE (SIZE(1..maxnoofPDUSessions)) OF PDUSessionResourceNotifyItem

PDUSessionResourceNotifyItem ::= SEQUENCE {
	pDUSessionID						PDUSessionID,
	pDUSessionResourceNotifyTransfer	OCTET STRING (CONTAINING PDUSessionResourceNotifyTransfer),
	iE-Extensions		ProtocolExtensionContainer { {PDUSessionResourceNotifyItem-ExtIEs} }	OPTIONAL,
	...
}

PDUSessionResourceNotifyItem-ExtIEs NGAP-PROTOCOL-EXTENSION ::= {
	...
}

PDUSessionResourceNotifyReleasedTransfer ::= SEQUENCE {
	cause				Cause,
	iE-Extensions		ProtocolExtensionContainer { {PDUSessionResourceNotifyReleasedTransfer-ExtIEs} }	OPTIONAL,
	...
}

PDUSessionResourceNotifyReleasedTransfer-ExtIEs NGAP-PROTOCOL-EXTENSION ::= {	
	{ ID id-SecondaryRATUsageInformation		CRITICALITY ignore	EXTENSION SecondaryRATUsageInformation		PRESENCE optional	},
	...
}

PDUSessionResourceNotifyTransfer ::= SEQUENCE {
	qosFlowNotifyList		QosFlowNotifyList														OPTIONAL,
	qosFlowReleasedList		QosFlowListWithCause													OPTIONAL,
	iE-Extensions		ProtocolExtensionContainer { {PDUSessionResourceNotifyTransfer-ExtIEs} }	OPTIONAL,
	...
}

PDUSessionResourceNotifyTransfer-ExtIEs NGAP-PROTOCOL-EXTENSION ::= {
	{ ID id-SecondaryRATUsageInformation		CRITICALITY ignore	EXTENSION SecondaryRATUsageInformation		PRESENCE optional	}|
	{ ID id-QosFlowFeedbackList					CRITICALITY ignore	EXTENSION QosFlowFeedbackList					PRESENCE optional	},
	...
}

PDUSessionResourceReleaseCommandTransfer ::= SEQUENCE {
	cause				Cause,
	iE-Extensions		ProtocolExtensionContainer { {PDUSessionResourceReleaseCommandTransfer-ExtIEs} }	OPTIONAL,
	...
}

PDUSessionResourceReleaseCommandTransfer-ExtIEs NGAP-PROTOCOL-EXTENSION ::= {
	...
}

PDUSessionResourceReleasedListNot ::= SEQUENCE (SIZE(1..maxnoofPDUSessions)) OF PDUSessionResourceReleasedItemNot

PDUSessionResourceReleasedItemNot ::= SEQUENCE {
	pDUSessionID									PDUSessionID,
	pDUSessionResourceNotifyReleasedTransfer		OCTET STRING (CONTAINING PDUSessionResourceNotifyReleasedTransfer),
	iE-Extensions		ProtocolExtensionContainer { {PDUSessionResourceReleasedItemNot-ExtIEs} }	OPTIONAL,
	...
}

PDUSessionResourceReleasedItemNot-ExtIEs NGAP-PROTOCOL-EXTENSION ::= {
	...
}

PDUSessionResourceReleasedListPSAck ::= SEQUENCE (SIZE(1..maxnoofPDUSessions)) OF PDUSessionResourceReleasedItemPSAck

PDUSessionResourceReleasedItemPSAck ::= SEQUENCE {
	pDUSessionID								PDUSessionID,
	pathSwitchRequestUnsuccessfulTransfer		OCTET STRING (CONTAINING PathSwitchRequestUnsuccessfulTransfer),
	iE-Extensions		ProtocolExtensionContainer { {PDUSessionResourceReleasedItemPSAck-ExtIEs} }	OPTIONAL,
	...
}

PDUSessionResourceReleasedItemPSAck-ExtIEs NGAP-PROTOCOL-EXTENSION ::= {
	...
}

PDUSessionResourceReleasedListPSFail ::= SEQUENCE (SIZE(1..maxnoofPDUSessions)) OF PDUSessionResourceReleasedItemPSFail

PDUSessionResourceReleasedItemPSFail ::= SEQUENCE {
	pDUSessionID								PDUSessionID,
	pathSwitchRequestUnsuccessfulTransfer		OCTET STRING (CONTAINING PathSwitchRequestUnsuccessfulTransfer),
	iE-Extensions		ProtocolExtensionContainer { {PDUSessionResourceReleasedItemPSFail-ExtIEs} }	OPTIONAL,
	...
}

PDUSessionResourceReleasedItemPSFail-ExtIEs NGAP-PROTOCOL-EXTENSION ::= {
	...
}

PDUSessionResourceReleasedListRelRes ::= SEQUENCE (SIZE(1..maxnoofPDUSessions)) OF PDUSessionResourceReleasedItemRelRes

PDUSessionResourceReleasedItemRelRes ::= SEQUENCE {
	pDUSessionID									PDUSessionID,
	pDUSessionResourceReleaseResponseTransfer		OCTET STRING (CONTAINING PDUSessionResourceReleaseResponseTransfer),
	iE-Extensions		ProtocolExtensionContainer { {PDUSessionResourceReleasedItemRelRes-ExtIEs} }	OPTIONAL,
	...
}

PDUSessionResourceReleasedItemRelRes-ExtIEs NGAP-PROTOCOL-EXTENSION ::= {
	...
}

PDUSessionResourceReleaseResponseTransfer ::= SEQUENCE {
	iE-Extensions		ProtocolExtensionContainer { {PDUSessionResourceReleaseResponseTransfer-ExtIEs} }	OPTIONAL,
	...
}

PDUSessionResourceReleaseResponseTransfer-ExtIEs NGAP-PROTOCOL-EXTENSION ::= {
	{ ID id-SecondaryRATUsageInformation		CRITICALITY ignore	EXTENSION SecondaryRATUsageInformation		PRESENCE optional	},
	...
}

PDUSessionResourceResumeListRESReq ::= SEQUENCE (SIZE(1..maxnoofPDUSessions)) OF PDUSessionResourceResumeItemRESReq

PDUSessionResourceResumeItemRESReq ::= SEQUENCE {
	pDUSessionID						PDUSessionID,
	uEContextResumeRequestTransfer		OCTET STRING (CONTAINING UEContextResumeRequestTransfer),
	iE-Extensions		ProtocolExtensionContainer { {PDUSessionResourceResumeItemRESReq-ExtIEs} }	OPTIONAL,
	...
}

PDUSessionResourceResumeItemRESReq-ExtIEs NGAP-PROTOCOL-EXTENSION ::= {
	...
}

PDUSessionResourceResumeListRESRes ::= SEQUENCE (SIZE(1..maxnoofPDUSessions)) OF PDUSessionResourceResumeItemRESRes

PDUSessionResourceResumeItemRESRes ::= SEQUENCE {
	pDUSessionID						PDUSessionID,
	uEContextResumeResponseTransfer		OCTET STRING (CONTAINING UEContextResumeResponseTransfer),
	iE-Extensions		ProtocolExtensionContainer { {PDUSessionResourceResumeItemRESRes-ExtIEs} }	OPTIONAL,
	...
}

PDUSessionResourceResumeItemRESRes-ExtIEs NGAP-PROTOCOL-EXTENSION ::= {
	...
}

PDUSessionResourceSecondaryRATUsageList ::= SEQUENCE (SIZE(1..maxnoofPDUSessions)) OF PDUSessionResourceSecondaryRATUsageItem

PDUSessionResourceSecondaryRATUsageItem ::= SEQUENCE {
	pDUSessionID							PDUSessionID,
	secondaryRATDataUsageReportTransfer		OCTET STRING (CONTAINING SecondaryRATDataUsageReportTransfer),
	iE-Extensions		ProtocolExtensionContainer { {PDUSessionResourceSecondaryRATUsageItem-ExtIEs} }	OPTIONAL,
	...
}

PDUSessionResourceSecondaryRATUsageItem-ExtIEs NGAP-PROTOCOL-EXTENSION ::= {
	...
}

PDUSessionResourceSetupListCxtReq ::= SEQUENCE (SIZE(1..maxnoofPDUSessions)) OF PDUSessionResourceSetupItemCxtReq

PDUSessionResourceSetupItemCxtReq ::= SEQUENCE {
	pDUSessionID								PDUSessionID,
	nAS-PDU										NAS-PDU												OPTIONAL,
	s-NSSAI										S-NSSAI,
	pDUSessionResourceSetupRequestTransfer		OCTET STRING (CONTAINING PDUSessionResourceSetupRequestTransfer),
	iE-Extensions		ProtocolExtensionContainer { {PDUSessionResourceSetupItemCxtReq-ExtIEs} }	OPTIONAL,
	...
}

PDUSessionResourceSetupItemCxtReq-ExtIEs NGAP-PROTOCOL-EXTENSION ::= {
	{ ID id-PduSessionExpectedUEActivityBehaviour			CRITICALITY ignore	EXTENSION ExpectedUEActivityBehaviour	PRESENCE optional	},
	...
}

PDUSessionResourceSetupListCxtRes ::= SEQUENCE (SIZE(1..maxnoofPDUSessions)) OF PDUSessionResourceSetupItemCxtRes

PDUSessionResourceSetupItemCxtRes ::= SEQUENCE {
	pDUSessionID								PDUSessionID,
	pDUSessionResourceSetupResponseTransfer		OCTET STRING (CONTAINING PDUSessionResourceSetupResponseTransfer),
	iE-Extensions		ProtocolExtensionContainer { {PDUSessionResourceSetupItemCxtRes-ExtIEs} }	OPTIONAL,
	...
}

PDUSessionResourceSetupItemCxtRes-ExtIEs NGAP-PROTOCOL-EXTENSION ::= {
	...
}

PDUSessionResourceSetupListHOReq ::= SEQUENCE (SIZE(1..maxnoofPDUSessions)) OF PDUSessionResourceSetupItemHOReq

PDUSessionResourceSetupItemHOReq ::= SEQUENCE {
	pDUSessionID				PDUSessionID,
	s-NSSAI						S-NSSAI,
	handoverRequestTransfer		OCTET STRING (CONTAINING PDUSessionResourceSetupRequestTransfer),
	iE-Extensions		ProtocolExtensionContainer { {PDUSessionResourceSetupItemHOReq-ExtIEs} }	OPTIONAL,
	...
}

PDUSessionResourceSetupItemHOReq-ExtIEs NGAP-PROTOCOL-EXTENSION ::= {
	{ ID id-PduSessionExpectedUEActivityBehaviour			CRITICALITY ignore	EXTENSION ExpectedUEActivityBehaviour	PRESENCE optional	},
	...
}

PDUSessionResourceSetupListSUReq ::= SEQUENCE (SIZE(1..maxnoofPDUSessions)) OF PDUSessionResourceSetupItemSUReq

PDUSessionResourceSetupItemSUReq ::= SEQUENCE {
	pDUSessionID								PDUSessionID,
	pDUSessionNAS-PDU							NAS-PDU												OPTIONAL,
	s-NSSAI										S-NSSAI,
	pDUSessionResourceSetupRequestTransfer		OCTET STRING (CONTAINING PDUSessionResourceSetupRequestTransfer),
	iE-Extensions		ProtocolExtensionContainer { {PDUSessionResourceSetupItemSUReq-ExtIEs} }	OPTIONAL,
	...
}

PDUSessionResourceSetupItemSUReq-ExtIEs NGAP-PROTOCOL-EXTENSION ::= {
	{ ID id-PduSessionExpectedUEActivityBehaviour			CRITICALITY ignore	EXTENSION ExpectedUEActivityBehaviour	PRESENCE optional	},
	...
}

PDUSessionResourceSetupListSURes ::= SEQUENCE (SIZE(1..maxnoofPDUSessions)) OF PDUSessionResourceSetupItemSURes

PDUSessionResourceSetupItemSURes ::= SEQUENCE {
	pDUSessionID											PDUSessionID,
	pDUSessionResourceSetupResponseTransfer					OCTET STRING (CONTAINING PDUSessionResourceSetupResponseTransfer),
	iE-Extensions		ProtocolExtensionContainer { {PDUSessionResourceSetupItemSURes-ExtIEs} }	OPTIONAL,
	...
}

PDUSessionResourceSetupItemSURes-ExtIEs NGAP-PROTOCOL-EXTENSION ::= {
	...
}

PDUSessionResourceSetupRequestTransfer ::= SEQUENCE {
	protocolIEs		ProtocolIE-Container		{ {PDUSessionResourceSetupRequestTransferIEs} },
	...
}

PDUSessionResourceSetupRequestTransferIEs NGAP-PROTOCOL-IES ::= {
	{ ID id-PDUSessionAggregateMaximumBitRate			CRITICALITY reject	TYPE PDUSessionAggregateMaximumBitRate		PRESENCE optional		}|
	{ ID id-UL-NGU-UP-TNLInformation					CRITICALITY reject	TYPE UPTransportLayerInformation				PRESENCE mandatory	}|
	{ ID id-AdditionalUL-NGU-UP-TNLInformation			CRITICALITY reject	TYPE UPTransportLayerInformationList			PRESENCE optional		}|
	{ ID id-DataForwardingNotPossible					CRITICALITY reject	TYPE DataForwardingNotPossible					PRESENCE optional		}|
	{ ID id-PDUSessionType								CRITICALITY reject	TYPE PDUSessionType									PRESENCE mandatory	}|
	{ ID id-SecurityIndication							CRITICALITY reject	TYPE SecurityIndication							PRESENCE optional		}|
	{ ID id-NetworkInstance								CRITICALITY reject	TYPE NetworkInstance								PRESENCE optional		}|
	{ ID id-QosFlowSetupRequestList						CRITICALITY reject	TYPE QosFlowSetupRequestList					PRESENCE mandatory	}|
	{ ID id-CommonNetworkInstance						CRITICALITY ignore	TYPE CommonNetworkInstance						PRESENCE optional		}|
	{ ID id-DirectForwardingPathAvailability			CRITICALITY ignore	TYPE DirectForwardingPathAvailability		PRESENCE optional	 	}|
	{ ID id-RedundantUL-NGU-UP-TNLInformation			CRITICALITY ignore	TYPE UPTransportLayerInformation				PRESENCE optional	 	}|
	{ ID id-AdditionalRedundantUL-NGU-UP-TNLInformation	CRITICALITY ignore	TYPE UPTransportLayerInformationList			PRESENCE optional		}|
	{ ID id-RedundantCommonNetworkInstance				CRITICALITY ignore	TYPE CommonNetworkInstance						PRESENCE optional		}|
	{ ID id-RedundantPDUSessionInformation				CRITICALITY ignore	TYPE RedundantPDUSessionInformation 			PRESENCE optional		},
	...
}

PDUSessionResourceSetupResponseTransfer ::= SEQUENCE {
	dLQosFlowPerTNLInformation				QosFlowPerTNLInformation,
	additionalDLQosFlowPerTNLInformation	QosFlowPerTNLInformationList										OPTIONAL,
	securityResult							SecurityResult														OPTIONAL,
	qosFlowFailedToSetupList				QosFlowListWithCause												OPTIONAL,
	iE-Extensions		ProtocolExtensionContainer { {PDUSessionResourceSetupResponseTransfer-ExtIEs} }		OPTIONAL,
	...
}

PDUSessionResourceSetupResponseTransfer-ExtIEs NGAP-PROTOCOL-EXTENSION ::= {
	{ ID id-RedundantDLQosFlowPerTNLInformation				CRITICALITY ignore	EXTENSION QosFlowPerTNLInformation			PRESENCE optional	 	}|
	{ ID id-AdditionalRedundantDLQosFlowPerTNLInformation	CRITICALITY ignore	EXTENSION QosFlowPerTNLInformationList		PRESENCE optional	 	}|
	{ ID id-UsedRSNInformation								CRITICALITY ignore	EXTENSION RedundantPDUSessionInformation	PRESENCE optional		}|
	{ ID id-GlobalRANNodeID 									CRITICALITY ignore	EXTENSION GlobalRANNodeID						PRESENCE optional		},
	...
}

PDUSessionResourceSetupUnsuccessfulTransfer ::= SEQUENCE {
	cause						Cause,
	criticalityDiagnostics		CriticalityDiagnostics																OPTIONAL,
	iE-Extensions		ProtocolExtensionContainer { {PDUSessionResourceSetupUnsuccessfulTransfer-ExtIEs} }	OPTIONAL,
	...
}

PDUSessionResourceSetupUnsuccessfulTransfer-ExtIEs NGAP-PROTOCOL-EXTENSION ::= {
	...
}

PDUSessionResourceSuspendListSUSReq ::= SEQUENCE (SIZE(1..maxnoofPDUSessions)) OF PDUSessionResourceSuspendItemSUSReq

PDUSessionResourceSuspendItemSUSReq ::= SEQUENCE {
	pDUSessionID						PDUSessionID,
	uEContextSuspendRequestTransfer		OCTET STRING (CONTAINING UEContextSuspendRequestTransfer),
	iE-Extensions		ProtocolExtensionContainer { {PDUSessionResourceSuspendItemSUSReq-ExtIEs} }	OPTIONAL,
	...
}

PDUSessionResourceSuspendItemSUSReq-ExtIEs NGAP-PROTOCOL-EXTENSION ::= {
	...
}

PDUSessionResourceSwitchedList ::= SEQUENCE (SIZE(1..maxnoofPDUSessions)) OF PDUSessionResourceSwitchedItem

PDUSessionResourceSwitchedItem ::= SEQUENCE {
	pDUSessionID								PDUSessionID,
	pathSwitchRequestAcknowledgeTransfer		OCTET STRING (CONTAINING PathSwitchRequestAcknowledgeTransfer),
	iE-Extensions		ProtocolExtensionContainer { { PDUSessionResourceSwitchedItem-ExtIEs} }	OPTIONAL,
	...
}

PDUSessionResourceSwitchedItem-ExtIEs NGAP-PROTOCOL-EXTENSION ::= {
	{ ID id-PduSessionExpectedUEActivityBehaviour			CRITICALITY ignore	EXTENSION ExpectedUEActivityBehaviour	PRESENCE optional	},
	...
}

PDUSessionResourceToBeSwitchedDLList ::= SEQUENCE (SIZE(1..maxnoofPDUSessions)) OF PDUSessionResourceToBeSwitchedDLItem

PDUSessionResourceToBeSwitchedDLItem ::= SEQUENCE {
	pDUSessionID					PDUSessionID,
	pathSwitchRequestTransfer		OCTET STRING (CONTAINING PathSwitchRequestTransfer),
	iE-Extensions		ProtocolExtensionContainer { { PDUSessionResourceToBeSwitchedDLItem-ExtIEs} }	OPTIONAL,
	...
}

PDUSessionResourceToBeSwitchedDLItem-ExtIEs NGAP-PROTOCOL-EXTENSION ::= {
	...
}

PDUSessionResourceToReleaseListHOCmd ::= SEQUENCE (SIZE(1..maxnoofPDUSessions)) OF PDUSessionResourceToReleaseItemHOCmd

PDUSessionResourceToReleaseItemHOCmd ::= SEQUENCE {
	pDUSessionID								PDUSessionID,
	handoverPreparationUnsuccessfulTransfer		OCTET STRING (CONTAINING HandoverPreparationUnsuccessfulTransfer),
	iE-Extensions		ProtocolExtensionContainer { {PDUSessionResourceToReleaseItemHOCmd-ExtIEs} }	OPTIONAL,
	...
}

PDUSessionResourceToReleaseItemHOCmd-ExtIEs NGAP-PROTOCOL-EXTENSION ::= {
	...
}

PDUSessionResourceToReleaseListRelCmd ::= SEQUENCE (SIZE(1..maxnoofPDUSessions)) OF PDUSessionResourceToReleaseItemRelCmd

PDUSessionResourceToReleaseItemRelCmd ::= SEQUENCE {
	pDUSessionID									PDUSessionID,
	pDUSessionResourceReleaseCommandTransfer		OCTET STRING (CONTAINING PDUSessionResourceReleaseCommandTransfer),
	iE-Extensions		ProtocolExtensionContainer { {PDUSessionResourceToReleaseItemRelCmd-ExtIEs} }	OPTIONAL,
	...
}

PDUSessionResourceToReleaseItemRelCmd-ExtIEs NGAP-PROTOCOL-EXTENSION ::= {
	...
}
PDUSessionType ::= ENUMERATED {
	ipv4,
	ipv6,
	ipv4v6,
	ethernet,
	unstructured,
	...
}

PDUSessionUsageReport ::= SEQUENCE {
	rATType								ENUMERATED {nr, eutra, ..., nr-unlicensed, e-utra-unlicensed},
	pDUSessionTimedReportList			VolumeTimedReportList,
	iE-Extensions		ProtocolExtensionContainer { {PDUSessionUsageReport-ExtIEs} } OPTIONAL,
	...
}

PDUSessionUsageReport-ExtIEs NGAP-PROTOCOL-EXTENSION ::= {
	...
}

Periodicity ::= INTEGER (0..640000, ...)

PeriodicRegistrationUpdateTimer ::= BIT STRING (SIZE(8))

PLMNIdentity ::= OCTET STRING (SIZE(3)) 

PLMNSupportList ::= SEQUENCE (SIZE(1..maxnoofPLMNs)) OF PLMNSupportItem

PLMNSupportItem ::= SEQUENCE {
	pLMNIdentity			PLMNIdentity,
	sliceSupportList		SliceSupportList,
	iE-Extensions		ProtocolExtensionContainer { {PLMNSupportItem-ExtIEs} } OPTIONAL,
	...
}

PLMNSupportItem-ExtIEs NGAP-PROTOCOL-EXTENSION ::= {
	{ ID id-NPN-Support						CRITICALITY reject	EXTENSION NPN-Support					PRESENCE optional	}|
	{ ID id-ExtendedSliceSupportList		CRITICALITY reject	EXTENSION ExtendedSliceSupportList 	PRESENCE optional	},
	...
}

PNI-NPN-MobilityInformation ::= SEQUENCE {
	allowed-PNI-NPI-List		Allowed-PNI-NPN-List,
	iE-Extensions				ProtocolExtensionContainer { {PNI-NPN-MobilityInformation-ExtIEs} }	OPTIONAL,
	...
}

PNI-NPN-MobilityInformation-ExtIEs NGAP-PROTOCOL-EXTENSION ::= {
	...
}

PortNumber ::= OCTET STRING (SIZE(2))

Pre-emptionCapability ::= ENUMERATED {
	shall-not-trigger-pre-emption,
	may-trigger-pre-emption,
	...
}

Pre-emptionVulnerability ::= ENUMERATED {
	not-pre-emptable,
	pre-emptable,
	...
}

PriorityLevelARP ::= INTEGER (1..15)

PriorityLevelQos ::= INTEGER (1..127, ...)

PWSFailedCellIDList ::= CHOICE {
	eUTRA-CGI-PWSFailedList		EUTRA-CGIList,
	nR-CGI-PWSFailedList		NR-CGIList,
	choice-Extensions		ProtocolIE-SingleContainer { {PWSFailedCellIDList-ExtIEs} }
}

PWSFailedCellIDList-ExtIEs NGAP-PROTOCOL-IES ::= {
	...
}

-- Q

QosCharacteristics ::= CHOICE {
	nonDynamic5QI		NonDynamic5QIDescriptor,
	dynamic5QI			Dynamic5QIDescriptor,
	choice-Extensions		ProtocolIE-SingleContainer { {QosCharacteristics-ExtIEs} }
}

QosCharacteristics-ExtIEs NGAP-PROTOCOL-IES ::= {
	...
}

QosFlowAcceptedList ::= SEQUENCE (SIZE(1..maxnoofQosFlows)) OF QosFlowAcceptedItem

QosFlowAcceptedItem ::= SEQUENCE {
	qosFlowIdentifier		QosFlowIdentifier,
	iE-Extensions		ProtocolExtensionContainer { {QosFlowAcceptedItem-ExtIEs} } OPTIONAL,
	...
}

QosFlowAcceptedItem-ExtIEs NGAP-PROTOCOL-EXTENSION ::= {
	{ ID id-CurrentQoSParaSetIndex	CRITICALITY ignore	EXTENSION AlternativeQoSParaSetIndex	PRESENCE optional	},
	...
}

QosFlowAddOrModifyRequestList ::= SEQUENCE (SIZE(1..maxnoofQosFlows)) OF QosFlowAddOrModifyRequestItem

QosFlowAddOrModifyRequestItem ::= SEQUENCE {
	qosFlowIdentifier				QosFlowIdentifier,
	qosFlowLevelQosParameters		QosFlowLevelQosParameters									OPTIONAL,
	e-RAB-ID						E-RAB-ID													OPTIONAL,
	iE-Extensions		ProtocolExtensionContainer { {QosFlowAddOrModifyRequestItem-ExtIEs} }	OPTIONAL,
	...
}

QosFlowAddOrModifyRequestItem-ExtIEs NGAP-PROTOCOL-EXTENSION ::= {
	{ID id-TSCTrafficCharacteristics	CRITICALITY ignore	EXTENSION TSCTrafficCharacteristics		PRESENCE optional }|
	{ID id-RedundantQosFlowIndicator	CRITICALITY ignore	EXTENSION RedundantQosFlowIndicator		PRESENCE optional },
	...
}

QosFlowAddOrModifyResponseList ::= SEQUENCE (SIZE(1..maxnoofQosFlows)) OF QosFlowAddOrModifyResponseItem

QosFlowAddOrModifyResponseItem ::= SEQUENCE {
	qosFlowIdentifier		QosFlowIdentifier,
	iE-Extensions		ProtocolExtensionContainer { {QosFlowAddOrModifyResponseItem-ExtIEs} }	OPTIONAL,
	...
}

QosFlowAddOrModifyResponseItem-ExtIEs NGAP-PROTOCOL-EXTENSION ::= {
	{ ID id-CurrentQoSParaSetIndex	CRITICALITY ignore	EXTENSION AlternativeQoSParaSetIndex	PRESENCE optional	},
	...
}

QosFlowFeedbackList ::= SEQUENCE (SIZE(1..maxnoofQosFlows)) OF QosFlowFeedbackItem

QosFlowFeedbackItem ::= SEQUENCE {
	qosFlowIdentifier			QosFlowIdentifier,
	updateFeedback				UpdateFeedback								OPTIONAL,
	cNpacketDelayBudgetDL		ExtendedPacketDelayBudget					OPTIONAL,
	cNpacketDelayBudgetUL		ExtendedPacketDelayBudget					OPTIONAL,
	iE-Extensions		ProtocolExtensionContainer { {QosFlowFeedbackItem-ExtIEs} }	OPTIONAL,
	...
}

QosFlowFeedbackItem-ExtIEs NGAP-PROTOCOL-EXTENSION ::= {
	...
}

QosFlowIdentifier ::= INTEGER (0..63, ...)

QosFlowInformationList ::= SEQUENCE (SIZE(1..maxnoofQosFlows)) OF QosFlowInformationItem

QosFlowInformationItem ::= SEQUENCE {
	qosFlowIdentifier	QosFlowIdentifier,
	dLForwarding		DLForwarding													OPTIONAL,
	iE-Extensions		ProtocolExtensionContainer { {QosFlowInformationItem-ExtIEs} }	OPTIONAL,
	...
}

QosFlowInformationItem-ExtIEs NGAP-PROTOCOL-EXTENSION ::= {
	{ID id-ULForwarding	CRITICALITY ignore	EXTENSION ULForwarding	PRESENCE optional},
	...
}

QosFlowLevelQosParameters ::= SEQUENCE {
	qosCharacteristics					QosCharacteristics,
	allocationAndRetentionPriority		AllocationAndRetentionPriority,
	gBR-QosInformation					GBR-QosInformation									OPTIONAL,
	reflectiveQosAttribute				ReflectiveQosAttribute								OPTIONAL,
	additionalQosFlowInformation		AdditionalQosFlowInformation						OPTIONAL,
	iE-Extensions		ProtocolExtensionContainer { {QosFlowLevelQosParameters-ExtIEs} }	OPTIONAL,
	...
}

QosFlowLevelQosParameters-ExtIEs NGAP-PROTOCOL-EXTENSION ::= {
	{ID id-QosMonitoringRequest	CRITICALITY ignore	EXTENSION QosMonitoringRequest	PRESENCE optional}|
	{ID id-QosMonitoringReportingFrequency	CRITICALITY ignore	EXTENSION QosMonitoringReportingFrequency	PRESENCE optional},
	...
}


QosMonitoringRequest ::= ENUMERATED {ul, dl, both, ..., stop}

QosMonitoringReportingFrequency ::= INTEGER (1..1800, ...)

QosFlowListWithCause ::= SEQUENCE (SIZE(1..maxnoofQosFlows)) OF QosFlowWithCauseItem

QosFlowWithCauseItem ::= SEQUENCE {
	qosFlowIdentifier		QosFlowIdentifier,
	cause					Cause,
	iE-Extensions		ProtocolExtensionContainer { {QosFlowWithCauseItem-ExtIEs} } OPTIONAL,
	...
}

QosFlowWithCauseItem-ExtIEs NGAP-PROTOCOL-EXTENSION ::= {
	...
}

QosFlowModifyConfirmList ::= SEQUENCE (SIZE(1..maxnoofQosFlows)) OF QosFlowModifyConfirmItem

QosFlowModifyConfirmItem ::= SEQUENCE {
	qosFlowIdentifier		QosFlowIdentifier,
	iE-Extensions		ProtocolExtensionContainer { {QosFlowModifyConfirmItem-ExtIEs} }	OPTIONAL,
	...
}

QosFlowModifyConfirmItem-ExtIEs NGAP-PROTOCOL-EXTENSION ::= {
	...
}

QosFlowNotifyList ::= SEQUENCE (SIZE(1..maxnoofQosFlows)) OF QosFlowNotifyItem

QosFlowNotifyItem ::= SEQUENCE {
	qosFlowIdentifier			QosFlowIdentifier,
	notificationCause			NotificationCause,
	iE-Extensions		ProtocolExtensionContainer { {QosFlowNotifyItem-ExtIEs} }	OPTIONAL,
	...
}

QosFlowNotifyItem-ExtIEs NGAP-PROTOCOL-EXTENSION ::= {
	{ ID id-CurrentQoSParaSetIndex	CRITICALITY ignore	EXTENSION AlternativeQoSParaSetNotifyIndex	PRESENCE optional	},
	...
}
QosFlowParametersList ::= SEQUENCE (SIZE(1..maxnoofQosFlows)) OF QosFlowParametersItem

QosFlowParametersItem ::= SEQUENCE {
	qosFlowIdentifier				QosFlowIdentifier,
	alternativeQoSParaSetList		AlternativeQoSParaSetList							OPTIONAL,	
	iE-Extensions		ProtocolExtensionContainer { {QosFlowParametersItem-ExtIEs} }	OPTIONAL,
	...
}

QosFlowParametersItem-ExtIEs NGAP-PROTOCOL-EXTENSION ::= {
	{ ID id-CNPacketDelayBudgetDL			CRITICALITY ignore	EXTENSION ExtendedPacketDelayBudget		PRESENCE optional	}|
	{ ID id-CNPacketDelayBudgetUL			CRITICALITY ignore	EXTENSION ExtendedPacketDelayBudget		PRESENCE optional	}|
	{ ID id-BurstArrivalTimeDownlink		CRITICALITY ignore	EXTENSION BurstArrivalTime					PRESENCE optional	},
	...
}

QosFlowPerTNLInformation ::= SEQUENCE {
	uPTransportLayerInformation		UPTransportLayerInformation,
	associatedQosFlowList			AssociatedQosFlowList,
	iE-Extensions		ProtocolExtensionContainer { { QosFlowPerTNLInformation-ExtIEs} }	OPTIONAL,
	...
}

QosFlowPerTNLInformation-ExtIEs NGAP-PROTOCOL-EXTENSION ::= {
	...
}

QosFlowPerTNLInformationList ::= SEQUENCE (SIZE(1..maxnoofMultiConnectivityMinusOne)) OF QosFlowPerTNLInformationItem

QosFlowPerTNLInformationItem ::= SEQUENCE {
	qosFlowPerTNLInformation				QosFlowPerTNLInformation,
	iE-Extensions		ProtocolExtensionContainer { { QosFlowPerTNLInformationItem-ExtIEs} }	OPTIONAL,
	...
}

QosFlowPerTNLInformationItem-ExtIEs NGAP-PROTOCOL-EXTENSION ::= {
	...
}

QosFlowSetupRequestList ::= SEQUENCE (SIZE(1..maxnoofQosFlows)) OF QosFlowSetupRequestItem

QosFlowSetupRequestItem ::= SEQUENCE {
	qosFlowIdentifier				QosFlowIdentifier,
	qosFlowLevelQosParameters		QosFlowLevelQosParameters,
	e-RAB-ID						E-RAB-ID											OPTIONAL,
	iE-Extensions		ProtocolExtensionContainer { {QosFlowSetupRequestItem-ExtIEs} } OPTIONAL,
	...
}

QosFlowSetupRequestItem-ExtIEs NGAP-PROTOCOL-EXTENSION ::= {
	{ID id-TSCTrafficCharacteristics	CRITICALITY ignore	EXTENSION TSCTrafficCharacteristics		PRESENCE optional }|
	{ID id-RedundantQosFlowIndicator	CRITICALITY ignore	EXTENSION RedundantQosFlowIndicator		PRESENCE optional },
	...
}

QosFlowListWithDataForwarding ::= SEQUENCE (SIZE(1..maxnoofQosFlows)) OF QosFlowItemWithDataForwarding

QosFlowItemWithDataForwarding ::= SEQUENCE {
	qosFlowIdentifier			QosFlowIdentifier,
	dataForwardingAccepted		DataForwardingAccepted											OPTIONAL,
	iE-Extensions		ProtocolExtensionContainer { {QosFlowItemWithDataForwarding-ExtIEs} }	OPTIONAL,
	...
}

QosFlowItemWithDataForwarding-ExtIEs NGAP-PROTOCOL-EXTENSION ::= {
	{ ID id-CurrentQoSParaSetIndex	CRITICALITY ignore	EXTENSION AlternativeQoSParaSetIndex	PRESENCE optional	},
	...
}

QosFlowToBeForwardedList ::= SEQUENCE (SIZE(1..maxnoofQosFlows)) OF QosFlowToBeForwardedItem

QosFlowToBeForwardedItem ::= SEQUENCE {
	qosFlowIdentifier		QosFlowIdentifier,
	iE-Extensions		ProtocolExtensionContainer { {QosFlowToBeForwardedItem-ExtIEs} }	OPTIONAL,
	...
}

QosFlowToBeForwardedItem-ExtIEs NGAP-PROTOCOL-EXTENSION ::= {
	...
}

QoSFlowsUsageReportList ::= SEQUENCE (SIZE(1..maxnoofQosFlows)) OF QoSFlowsUsageReport-Item

QoSFlowsUsageReport-Item ::= SEQUENCE {
	qosFlowIdentifier					QosFlowIdentifier,
	rATType								ENUMERATED {nr, eutra, ..., nr-unlicensed, e-utra-unlicensed},
	qoSFlowsTimedReportList				VolumeTimedReportList,
	iE-Extensions		ProtocolExtensionContainer { {QoSFlowsUsageReport-Item-ExtIEs} } OPTIONAL,
	...
}

QoSFlowsUsageReport-Item-ExtIEs NGAP-PROTOCOL-EXTENSION ::= {
	...
}

-- R

Range ::= ENUMERATED {m50, m80, m180, m200, m350, m400, m500, m700, m1000, ...}

RANNodeName ::= PrintableString (SIZE(1..150, ...))

RANNodeNameVisibleString ::= VisibleString (SIZE(1..150, ...))

RANNodeNameUTF8String ::= UTF8String (SIZE(1..150, ...))

RANPagingPriority ::= INTEGER (1..256)

RANStatusTransfer-TransparentContainer ::= SEQUENCE {
	dRBsSubjectToStatusTransferList		DRBsSubjectToStatusTransferList,
	iE-Extensions		ProtocolExtensionContainer { {RANStatusTransfer-TransparentContainer-ExtIEs} }	OPTIONAL,
	...
}

RANStatusTransfer-TransparentContainer-ExtIEs NGAP-PROTOCOL-EXTENSION ::= {
	...
}

RAN-UE-NGAP-ID ::= INTEGER (0..4294967295)

RAT-Information ::= ENUMERATED {
	unlicensed,
	nb-IoT,
	...
}

RATRestrictions ::= SEQUENCE (SIZE(1..maxnoofEPLMNsPlusOne)) OF RATRestrictions-Item

RATRestrictions-Item ::= SEQUENCE {
	pLMNIdentity					PLMNIdentity,
	rATRestrictionInformation		RATRestrictionInformation,
	iE-Extensions		ProtocolExtensionContainer { {RATRestrictions-Item-ExtIEs} }		OPTIONAL,
	...
}

RATRestrictions-Item-ExtIEs NGAP-PROTOCOL-EXTENSION ::= {
	{ ID id-ExtendedRATRestrictionInformation		CRITICALITY ignore	EXTENSION ExtendedRATRestrictionInformation		PRESENCE optional	},
	...
}

RATRestrictionInformation ::= BIT STRING (SIZE(8, ...))

RecommendedCellsForPaging ::= SEQUENCE {
	recommendedCellList			RecommendedCellList,
	iE-Extensions		ProtocolExtensionContainer { {RecommendedCellsForPaging-ExtIEs} }	OPTIONAL,
	...
}

RecommendedCellsForPaging-ExtIEs NGAP-PROTOCOL-EXTENSION ::= {
	...
}

RecommendedCellList ::= SEQUENCE (SIZE(1..maxnoofRecommendedCells)) OF RecommendedCellItem

RecommendedCellItem ::= SEQUENCE {
	nGRAN-CGI				NGRAN-CGI,
	timeStayedInCell		INTEGER (0..4095)		OPTIONAL,
	iE-Extensions		ProtocolExtensionContainer { {RecommendedCellItem-ExtIEs} }	OPTIONAL,
	...
}

RecommendedCellItem-ExtIEs NGAP-PROTOCOL-EXTENSION ::= {
	...
}

RecommendedRANNodesForPaging ::= SEQUENCE {
	recommendedRANNodeList		RecommendedRANNodeList,
	iE-Extensions		ProtocolExtensionContainer { {RecommendedRANNodesForPaging-ExtIEs} }	OPTIONAL,
	...
}

RecommendedRANNodesForPaging-ExtIEs NGAP-PROTOCOL-EXTENSION ::= {
	...
}

RecommendedRANNodeList::= SEQUENCE (SIZE(1..maxnoofRecommendedRANNodes)) OF RecommendedRANNodeItem

RecommendedRANNodeItem ::= SEQUENCE {
	aMFPagingTarget		AMFPagingTarget,
	iE-Extensions		ProtocolExtensionContainer { {RecommendedRANNodeItem-ExtIEs} }	OPTIONAL,
	...
}

RecommendedRANNodeItem-ExtIEs NGAP-PROTOCOL-EXTENSION ::= {
	...
}

RedirectionVoiceFallback ::= ENUMERATED {
	possible,
	not-possible,
	...
}

RedundantPDUSessionInformation ::= SEQUENCE {
	rSN					RSN,
	iE-Extensions		ProtocolExtensionContainer { {RedundantPDUSessionInformation-ExtIEs} }	OPTIONAL,
	...
}

RedundantPDUSessionInformation-ExtIEs NGAP-PROTOCOL-EXTENSION ::= {
	...
}

RedundantQosFlowIndicator ::= ENUMERATED {true, false}

ReflectiveQosAttribute ::= ENUMERATED {
	subject-to,
	...
}

RelativeAMFCapacity ::= INTEGER (0..255)

ReportArea ::= ENUMERATED {
	cell,
	...
}

RepetitionPeriod ::= INTEGER (0..131071)

ResetAll ::= ENUMERATED {
	reset-all,
	...
}

ReportAmountMDT ::= ENUMERATED {
	r1, r2, r4, r8, r16, r32, r64, rinfinity
}

ReportIntervalMDT ::= ENUMERATED {
	ms120, ms240, ms480, ms640, ms1024, ms2048, ms5120, ms10240, min1, min6, min12, min30, min60
} 

ResetType ::= CHOICE {
	nG-Interface			ResetAll,
	partOfNG-Interface		UE-associatedLogicalNG-connectionList,
	choice-Extensions		ProtocolIE-SingleContainer { {ResetType-ExtIEs} }
}

ResetType-ExtIEs NGAP-PROTOCOL-IES ::= {
	...
}

RGLevelWirelineAccessCharacteristics ::= OCTET STRING

RNC-ID ::= INTEGER (0..4095)

RoutingID ::= OCTET STRING

RRCContainer ::= OCTET STRING

RRCEstablishmentCause ::= ENUMERATED {
	emergency,
	highPriorityAccess,
	mt-Access,
	mo-Signalling,
	mo-Data,
	mo-VoiceCall,
	mo-VideoCall,
	mo-SMS,
	mps-PriorityAccess,
	mcs-PriorityAccess,
	...,
	notAvailable,
	mo-ExceptionData
}

RRCInactiveTransitionReportRequest ::= ENUMERATED {
	subsequent-state-transition-report,
	single-rrc-connected-state-report,
	cancel-report,
	...
}

RRCState ::= ENUMERATED {
	inactive,
	connected,
	...
}

RSN ::= ENUMERATED {v1, v2, ...}

RIMInformationTransfer ::= SEQUENCE {
	targetRANNodeID				TargetRANNodeID,
	sourceRANNodeID				SourceRANNodeID,
	rIMInformation				RIMInformation,
	iE-Extensions				ProtocolExtensionContainer { {RIMInformationTransfer-ExtIEs} }	OPTIONAL,
	...
}

RIMInformationTransfer-ExtIEs NGAP-PROTOCOL-EXTENSION ::= {
	...
}


RIMInformation	::= SEQUENCE		{
	targetgNBSetID			GNBSetID,
	rIM-RSDetection			ENUMERATED	{rs-detected, rs-disappeared, ...},
	iE-Extensions			ProtocolExtensionContainer { {RIMInformation-ExtIEs} }	OPTIONAL,
	...
}

RIMInformation-ExtIEs NGAP-PROTOCOL-EXTENSION ::= {
	...
}

GNBSetID ::= BIT STRING (SIZE(22))

-- S

ScheduledCommunicationTime ::= SEQUENCE {
	dayofWeek			BIT STRING (SIZE(7))												OPTIONAL,
	timeofDayStart		INTEGER (0..86399, ...)												OPTIONAL,
	timeofDayEnd		INTEGER (0..86399, ...)												OPTIONAL,
	iE-Extensions		ProtocolExtensionContainer { { ScheduledCommunicationTime-ExtIEs}}	OPTIONAL,
	...
}

ScheduledCommunicationTime-ExtIEs NGAP-PROTOCOL-EXTENSION ::= {
	...
}

SCTP-TLAs	::= SEQUENCE (SIZE(1..maxnoofXnTLAs)) OF TransportLayerAddress

SD ::= OCTET STRING (SIZE(3))

SecondaryRATUsageInformation ::= SEQUENCE {
	pDUSessionUsageReport		PDUSessionUsageReport											OPTIONAL,
	qosFlowsUsageReportList		QoSFlowsUsageReportList											OPTIONAL,
	iE-Extension		ProtocolExtensionContainer { {SecondaryRATUsageInformation-ExtIEs} }	OPTIONAL,
	...
}

SecondaryRATUsageInformation-ExtIEs NGAP-PROTOCOL-EXTENSION ::= {
	...
}

SecondaryRATDataUsageReportTransfer ::= SEQUENCE {
	secondaryRATUsageInformation		SecondaryRATUsageInformation									OPTIONAL,
	iE-Extensions		ProtocolExtensionContainer { {SecondaryRATDataUsageReportTransfer-ExtIEs} }	OPTIONAL,
	...
}

SecondaryRATDataUsageReportTransfer-ExtIEs NGAP-PROTOCOL-EXTENSION ::= {
	...
}

SecurityContext ::= SEQUENCE {
	nextHopChainingCount		NextHopChainingCount,
	nextHopNH					SecurityKey,
	iE-Extensions		ProtocolExtensionContainer { {SecurityContext-ExtIEs} }	OPTIONAL,
	...
}

SecurityContext-ExtIEs NGAP-PROTOCOL-EXTENSION ::= {
	...
}

SecurityIndication ::= SEQUENCE {
	integrityProtectionIndication				IntegrityProtectionIndication,
	confidentialityProtectionIndication			ConfidentialityProtectionIndication,
	maximumIntegrityProtectedDataRate-UL			MaximumIntegrityProtectedDataRate		OPTIONAL,
-- The above IE shall be present if integrity protection is required or preferred
	iE-Extensions		ProtocolExtensionContainer { {SecurityIndication-ExtIEs} }		OPTIONAL,
	...
}

SecurityIndication-ExtIEs NGAP-PROTOCOL-EXTENSION ::= {
	{ ID id-MaximumIntegrityProtectedDataRate-DL	CRITICALITY ignore	EXTENSION MaximumIntegrityProtectedDataRate	PRESENCE optional	},
	...
}

SecurityKey	::= BIT STRING (SIZE(256))

SecurityResult ::= SEQUENCE {
	integrityProtectionResult			IntegrityProtectionResult,
	confidentialityProtectionResult		ConfidentialityProtectionResult,
	iE-Extensions		ProtocolExtensionContainer { {SecurityResult-ExtIEs} }	OPTIONAL,
	...
}

SecurityResult-ExtIEs NGAP-PROTOCOL-EXTENSION ::= {
	...
}

SensorMeasurementConfiguration ::=	SEQUENCE {
	sensorMeasConfig            SensorMeasConfig,
	sensorMeasConfigNameList	SensorMeasConfigNameList            								OPTIONAL,
	iE-Extensions		ProtocolExtensionContainer { {SensorMeasurementConfiguration-ExtIEs} } 	OPTIONAL,
	...
}

SensorMeasurementConfiguration-ExtIEs NGAP-PROTOCOL-EXTENSION ::= {
	...
}

SensorMeasConfigNameList ::= SEQUENCE (SIZE(1..maxnoofSensorName)) OF SensorMeasConfigNameItem

SensorMeasConfigNameItem ::= SEQUENCE {
	sensorNameConfig		SensorNameConfig,
	iE-Extensions		ProtocolExtensionContainer { { SensorMeasConfigNameItem-ExtIEs } } 	OPTIONAL,
	...
}

SensorMeasConfigNameItem-ExtIEs NGAP-PROTOCOL-EXTENSION ::= {
	...
}

SensorMeasConfig::= ENUMERATED {setup,...}

SensorNameConfig ::= CHOICE {
	uncompensatedBarometricConfig		ENUMERATED {true, ...},
	ueSpeedConfig						ENUMERATED {true, ...},
	ueOrientationConfig					ENUMERATED {true, ...},
	choice-Extensions		ProtocolIE-SingleContainer { {SensorNameConfig-ExtIEs} }
}

SensorNameConfig-ExtIEs NGAP-PROTOCOL-IES ::= {
	...
}

SerialNumber ::= BIT STRING (SIZE(16))

ServedGUAMIList ::= SEQUENCE (SIZE(1..maxnoofServedGUAMIs)) OF ServedGUAMIItem

ServedGUAMIItem ::= SEQUENCE {
	gUAMI				GUAMI,
	backupAMFName		AMFName													OPTIONAL,
	iE-Extensions		ProtocolExtensionContainer { {ServedGUAMIItem-ExtIEs} }	OPTIONAL,
	...
}

ServedGUAMIItem-ExtIEs NGAP-PROTOCOL-EXTENSION ::= {
	{ID id-GUAMIType		CRITICALITY ignore	EXTENSION GUAMIType		PRESENCE optional	},
	...
}

ServiceAreaInformation ::= SEQUENCE (SIZE(1.. maxnoofEPLMNsPlusOne)) OF ServiceAreaInformation-Item

ServiceAreaInformation-Item ::= SEQUENCE {
	pLMNIdentity		PLMNIdentity,
	allowedTACs			AllowedTACs																OPTIONAL,
	notAllowedTACs		NotAllowedTACs															OPTIONAL,
	iE-Extensions		ProtocolExtensionContainer { {ServiceAreaInformation-Item-ExtIEs} }		OPTIONAL,
	...
}

ServiceAreaInformation-Item-ExtIEs NGAP-PROTOCOL-EXTENSION ::= {
	...
}

SgNB-UE-X2AP-ID ::= INTEGER (0..4294967295)

SliceOverloadList ::= SEQUENCE (SIZE(1..maxnoofSliceItems)) OF SliceOverloadItem

SliceOverloadItem ::= SEQUENCE {
	s-NSSAI				S-NSSAI,
	iE-Extensions		ProtocolExtensionContainer { {SliceOverloadItem-ExtIEs} }	OPTIONAL,
	...
}

SliceOverloadItem-ExtIEs NGAP-PROTOCOL-EXTENSION ::= {
	...
}

SliceSupportList ::= SEQUENCE (SIZE(1..maxnoofSliceItems)) OF SliceSupportItem

SliceSupportItem ::= SEQUENCE {
	s-NSSAI				S-NSSAI,
	iE-Extensions		ProtocolExtensionContainer { {SliceSupportItem-ExtIEs} }	OPTIONAL,
	...
}

SliceSupportItem-ExtIEs NGAP-PROTOCOL-EXTENSION ::= {
	...
}

SNPN-MobilityInformation ::= SEQUENCE {
	serving-NID			NID,
	iE-Extensions		ProtocolExtensionContainer { {SNPN-MobilityInformation-ExtIEs} }	OPTIONAL,
	...
}

SNPN-MobilityInformation-ExtIEs NGAP-PROTOCOL-EXTENSION ::= {
	...
}

S-NSSAI ::= SEQUENCE {
	sST					SST,
	sD					SD													OPTIONAL,
	iE-Extensions		ProtocolExtensionContainer { { S-NSSAI-ExtIEs} }	OPTIONAL,
	...
}

S-NSSAI-ExtIEs NGAP-PROTOCOL-EXTENSION ::= {
	...
}

SONConfigurationTransfer ::= SEQUENCE {
	targetRANNodeID				TargetRANNodeID,
	sourceRANNodeID				SourceRANNodeID,
	sONInformation				SONInformation,
	xnTNLConfigurationInfo		XnTNLConfigurationInfo										OPTIONAL,
-- The above IE shall be present if the SON Information IE contains the SON Information Request IE set to Xn TNL Configuration Info
	iE-Extensions		ProtocolExtensionContainer { {SONConfigurationTransfer-ExtIEs} }	OPTIONAL,
	...
}

SONConfigurationTransfer-ExtIEs NGAP-PROTOCOL-EXTENSION ::= {
	...
}

SONInformation ::= CHOICE {
	sONInformationRequest		SONInformationRequest,
	sONInformationReply			SONInformationReply,
	choice-Extensions		ProtocolIE-SingleContainer { {SONInformation-ExtIEs} }
}

SONInformation-ExtIEs NGAP-PROTOCOL-IES ::= {
	{ ID id-SONInformationReport		CRITICALITY ignore	TYPE SONInformationReport		PRESENCE mandatory	},
	...
}

SONInformationReply ::= SEQUENCE {
	xnTNLConfigurationInfo		XnTNLConfigurationInfo									OPTIONAL,
	iE-Extensions		ProtocolExtensionContainer { {SONInformationReply-ExtIEs} }		OPTIONAL,
	...
}

SONInformationReply-ExtIEs NGAP-PROTOCOL-EXTENSION ::= {
	...
}

SONInformationReport::= CHOICE {
	failureIndicationInformation	FailureIndication,
	hOReportInformation				HOReport,
	choice-Extensions		ProtocolIE-SingleContainer { { SONInformationReport-ExtIEs} }
}

SONInformationReport-ExtIEs NGAP-PROTOCOL-IES ::= {
	...
}

SONInformationRequest ::= ENUMERATED { 
	xn-TNL-configuration-info,
	...
}

SourceNGRANNode-ToTargetNGRANNode-TransparentContainer ::= SEQUENCE {
	rRCContainer							RRCContainer,
	pDUSessionResourceInformationList		PDUSessionResourceInformationList													OPTIONAL,
	e-RABInformationList					E-RABInformationList																OPTIONAL,
	targetCell-ID							NGRAN-CGI,
	indexToRFSP								IndexToRFSP																			OPTIONAL,
	uEHistoryInformation					UEHistoryInformation,
	iE-Extensions		ProtocolExtensionContainer { {SourceNGRANNode-ToTargetNGRANNode-TransparentContainer-ExtIEs} }	OPTIONAL,
	...
}

SourceNGRANNode-ToTargetNGRANNode-TransparentContainer-ExtIEs NGAP-PROTOCOL-EXTENSION ::= {
	{ ID id-SgNB-UE-X2AP-ID	CRITICALITY ignore	EXTENSION SgNB-UE-X2AP-ID 												PRESENCE optional		}|
	{ ID id-UEHistoryInformationFromTheUE		CRITICALITY ignore	EXTENSION UEHistoryInformationFromTheUE		PRESENCE optional		},
	...
}

SourceOfUEActivityBehaviourInformation ::= ENUMERATED {
	subscription-information,
	statistics,
	...
}

SourceRANNodeID ::= SEQUENCE {
	globalRANNodeID		GlobalRANNodeID,
	selectedTAI			TAI,
	iE-Extensions		ProtocolExtensionContainer { {SourceRANNodeID-ExtIEs} } OPTIONAL,
	...
}

SourceRANNodeID-ExtIEs NGAP-PROTOCOL-EXTENSION ::= {
	...
}

SourceToTarget-TransparentContainer ::= OCTET STRING
-- This IE includes a transparent container from the source RAN node to the target RAN node. 
-- The octets of the OCTET STRING are encoded according to the specifications of the target system.

SourceToTarget-AMFInformationReroute ::= SEQUENCE {
	configuredNSSAI					ConfiguredNSSAI														OPTIONAL,
	rejectedNSSAIinPLMN				RejectedNSSAIinPLMN													OPTIONAL,
	rejectedNSSAIinTA				RejectedNSSAIinTA													OPTIONAL,
	iE-Extensions		ProtocolExtensionContainer { {SourceToTarget-AMFInformationReroute-ExtIEs} }	OPTIONAL,
	...
}

SourceToTarget-AMFInformationReroute-ExtIEs NGAP-PROTOCOL-EXTENSION ::= {
	...
}

-- This IE includes information from the source Core node to the target Core node for reroute information provide by NSSF. 
-- The octets of the OCTET STRING are encoded according to the specifications of the Core network.

SRVCCOperationPossible ::= ENUMERATED {
	possible, 
	notPossible,
	...
}

ConfiguredNSSAI  ::=  OCTET STRING (SIZE(128))

RejectedNSSAIinPLMN ::= OCTET STRING (SIZE(32))

RejectedNSSAIinTA ::= OCTET STRING (SIZE(32))

SST ::= OCTET STRING (SIZE(1))

SupportedTAList ::= SEQUENCE (SIZE(1..maxnoofTACs)) OF SupportedTAItem

SupportedTAItem ::= SEQUENCE {
	tAC									TAC,
	broadcastPLMNList		BroadcastPLMNList,
	iE-Extensions		ProtocolExtensionContainer { {SupportedTAItem-ExtIEs} } OPTIONAL,
	...
}

SupportedTAItem-ExtIEs NGAP-PROTOCOL-EXTENSION ::= {
	{ID id-ConfiguredTACIndication		CRITICALITY ignore	EXTENSION ConfiguredTACIndication	PRESENCE optional	}|
	{ID id-RAT-Information				CRITICALITY reject	EXTENSION RAT-Information			PRESENCE optional	},
	...
}

SuspendIndicator ::= ENUMERATED {
	true,
	...
}

Suspend-Request-Indication ::= ENUMERATED {
	suspend-requested,
	...
}

Suspend-Response-Indication ::= ENUMERATED {
	suspend-indicated,
	...
}

-- T

TAC ::= OCTET STRING (SIZE(3))

TAI ::= SEQUENCE {
	pLMNIdentity		PLMNIdentity,
	tAC					TAC,
	iE-Extensions		ProtocolExtensionContainer { {TAI-ExtIEs} } OPTIONAL,
	...
}

TAI-ExtIEs NGAP-PROTOCOL-EXTENSION ::= {
	...
}

TAIBroadcastEUTRA ::= SEQUENCE (SIZE(1..maxnoofTAIforWarning)) OF TAIBroadcastEUTRA-Item

TAIBroadcastEUTRA-Item ::= SEQUENCE {
	tAI								TAI,
	completedCellsInTAI-EUTRA		CompletedCellsInTAI-EUTRA,
	iE-Extensions		ProtocolExtensionContainer { {TAIBroadcastEUTRA-Item-ExtIEs} } OPTIONAL,
	...
}

TAIBroadcastEUTRA-Item-ExtIEs NGAP-PROTOCOL-EXTENSION ::= {
	...
}

TAIBroadcastNR ::= SEQUENCE (SIZE(1..maxnoofTAIforWarning)) OF TAIBroadcastNR-Item

TAIBroadcastNR-Item ::= SEQUENCE {
	tAI							TAI,
	completedCellsInTAI-NR		CompletedCellsInTAI-NR,
	iE-Extensions		ProtocolExtensionContainer { {TAIBroadcastNR-Item-ExtIEs} } OPTIONAL,
	...
}

TAIBroadcastNR-Item-ExtIEs NGAP-PROTOCOL-EXTENSION ::= {
	...
}

TAICancelledEUTRA ::= SEQUENCE (SIZE(1..maxnoofTAIforWarning)) OF TAICancelledEUTRA-Item

TAICancelledEUTRA-Item ::= SEQUENCE {
	tAI								TAI,
	cancelledCellsInTAI-EUTRA		CancelledCellsInTAI-EUTRA,
	iE-Extensions		ProtocolExtensionContainer { {TAICancelledEUTRA-Item-ExtIEs} } OPTIONAL,
	...
}

TAICancelledEUTRA-Item-ExtIEs NGAP-PROTOCOL-EXTENSION ::= {
	...
}

TAICancelledNR ::= SEQUENCE (SIZE(1..maxnoofTAIforWarning)) OF TAICancelledNR-Item

TAICancelledNR-Item ::= SEQUENCE {
	tAI							TAI,
	cancelledCellsInTAI-NR		CancelledCellsInTAI-NR,
	iE-Extensions		ProtocolExtensionContainer { {TAICancelledNR-Item-ExtIEs} } OPTIONAL,
	...
}

TAICancelledNR-Item-ExtIEs NGAP-PROTOCOL-EXTENSION ::= {
	...
}

TAIListForInactive ::= SEQUENCE (SIZE(1..maxnoofTAIforInactive)) OF TAIListForInactiveItem

TAIListForInactiveItem ::= SEQUENCE {
	tAI					TAI,
	iE-Extensions		ProtocolExtensionContainer { {TAIListForInactiveItem-ExtIEs} } OPTIONAL,
	...
}

TAIListForInactiveItem-ExtIEs NGAP-PROTOCOL-EXTENSION ::= {
	...
}

TAIListForPaging ::= SEQUENCE (SIZE(1..maxnoofTAIforPaging)) OF TAIListForPagingItem

TAIListForPagingItem ::= SEQUENCE {
	tAI					TAI,
	iE-Extensions		ProtocolExtensionContainer { {TAIListForPagingItem-ExtIEs} } OPTIONAL,
	...
}

TAIListForPagingItem-ExtIEs NGAP-PROTOCOL-EXTENSION ::= {
	...
}

TAIListForRestart ::= SEQUENCE (SIZE(1..maxnoofTAIforRestart)) OF TAI

TAIListForWarning ::= SEQUENCE (SIZE(1..maxnoofTAIforWarning)) OF TAI

TargeteNB-ID ::= SEQUENCE {
	globalENB-ID		GlobalNgENB-ID,
	selected-EPS-TAI	EPS-TAI,
	iE-Extensions		ProtocolExtensionContainer { {TargeteNB-ID-ExtIEs} } OPTIONAL,
	...
}

TargeteNB-ID-ExtIEs NGAP-PROTOCOL-EXTENSION ::= {
	...
}

TargetID ::= CHOICE {
	targetRANNodeID			TargetRANNodeID,
	targeteNB-ID			TargeteNB-ID,
	choice-Extensions		ProtocolIE-SingleContainer { {TargetID-ExtIEs} }
}

TargetID-ExtIEs NGAP-PROTOCOL-IES ::= {
	{ID id-TargetRNC-ID		CRITICALITY reject	TYPE TargetRNC-ID PRESENCE mandatory },
	...
}

TargetNGRANNode-ToSourceNGRANNode-TransparentContainer ::= SEQUENCE {
	rRCContainer		RRCContainer,
	iE-Extensions		ProtocolExtensionContainer { {TargetNGRANNode-ToSourceNGRANNode-TransparentContainer-ExtIEs} } OPTIONAL,
	...
}

TargetNGRANNode-ToSourceNGRANNode-TransparentContainer-ExtIEs NGAP-PROTOCOL-EXTENSION ::= {
	{ ID id-DAPSResponseInfoList						CRITICALITY ignore	EXTENSION DAPSResponseInfoList	PRESENCE optional },
	...
}

TargetNGRANNode-ToSourceNGRANNode-FailureTransparentContainer ::= SEQUENCE {
	cell-CAGInformation		Cell-CAGInformation			OPTIONAL,
	iE-Extensions			ProtocolExtensionContainer { {TargetNGRANNode-ToSourceNGRANNode-FailureTransparentContainer-ExtIEs} } OPTIONAL,
	...
}

TargetNGRANNode-ToSourceNGRANNode-FailureTransparentContainer-ExtIEs NGAP-PROTOCOL-EXTENSION ::= {
	...
}

TargetRANNodeID ::= SEQUENCE {
	globalRANNodeID		GlobalRANNodeID,
	selectedTAI			TAI,
	iE-Extensions		ProtocolExtensionContainer { {TargetRANNodeID-ExtIEs} } OPTIONAL,
	...
}

TargetRANNodeID-ExtIEs NGAP-PROTOCOL-EXTENSION ::= {
	...
}

TargetRNC-ID ::= SEQUENCE {
	lAI					LAI,
	rNC-ID				RNC-ID,
	extendedRNC-ID		ExtendedRNC-ID											OPTIONAL,
	iE-Extensions		ProtocolExtensionContainer { {TargetRNC-ID-ExtIEs} } 	OPTIONAL,
	...
}

TargetRNC-ID-ExtIEs NGAP-PROTOCOL-EXTENSION ::= {
	...
}

TargetToSource-TransparentContainer ::= OCTET STRING
-- This IE includes a transparent container from the target RAN node to the source RAN node. 
-- The octets of the OCTET STRING are encoded according to the specifications of the target system.

TargettoSource-Failure-TransparentContainer ::= OCTET STRING
-- This IE includes a transparent container from the target RAN node to the source RAN node. 
-- The octets of the OCTET STRING are encoded according to the specifications of the target system (if applicable).

TimerApproachForGUAMIRemoval ::= ENUMERATED { 
	apply-timer,
	...
}

TimeStamp ::= OCTET STRING (SIZE(4))

TimeToWait ::= ENUMERATED {v1s, v2s, v5s, v10s, v20s, v60s, ...}

TimeUEStayedInCell ::= INTEGER (0..4095)

TimeUEStayedInCellEnhancedGranularity ::= INTEGER (0..40950)

TNAP-ID ::= OCTET STRING 

TNGF-ID ::= CHOICE {
	tNGF-ID				 	BIT STRING (SIZE(32, ...)),
	choice-Extensions		ProtocolIE-SingleContainer { {TNGF-ID-ExtIEs} }
}

TNGF-ID-ExtIEs NGAP-PROTOCOL-IES ::= {
	...
}

TNLAddressWeightFactor ::= INTEGER (0..255)

TNLAssociationList ::= SEQUENCE (SIZE(1..maxnoofTNLAssociations)) OF TNLAssociationItem

TNLAssociationItem ::= SEQUENCE {
	tNLAssociationAddress		CPTransportLayerInformation,
	cause						Cause,
	iE-Extensions		ProtocolExtensionContainer { {TNLAssociationItem-ExtIEs} } OPTIONAL,
	...
}

TNLAssociationItem-ExtIEs NGAP-PROTOCOL-EXTENSION ::= {
	...
}

TNLAssociationUsage ::= ENUMERATED { 
	ue,
	non-ue,
	both,
	...
}

TooearlyIntersystemHO::= SEQUENCE {
	sourcecellID			EUTRA-CGI,
	failurecellID			NGRAN-CGI,
	uERLFReportContainer	UERLFReportContainer		OPTIONAL,
	iE-Extensions			ProtocolExtensionContainer { { TooearlyIntersystemHO-ExtIEs} }			OPTIONAL,
	...
}

TooearlyIntersystemHO-ExtIEs NGAP-PROTOCOL-EXTENSION ::= {
	...
}

TraceActivation ::= SEQUENCE {
	nGRANTraceID						NGRANTraceID,
	interfacesToTrace					InterfacesToTrace,
traceDepth							TraceDepth,
traceCollectionEntityIPAddress		TransportLayerAddress,
	iE-Extensions		ProtocolExtensionContainer { {TraceActivation-ExtIEs} }	OPTIONAL,
	...
}

TraceActivation-ExtIEs NGAP-PROTOCOL-EXTENSION ::= {
	{ ID id-MDTConfiguration			CRITICALITY ignore	EXTENSION MDT-Configuration		PRESENCE optional 	}|
	{ ID id-TraceCollectionEntityURI	CRITICALITY ignore	EXTENSION URI-address			PRESENCE optional		},
	...
}

TraceDepth ::= ENUMERATED { 
	minimum,
	medium,
	maximum,
	minimumWithoutVendorSpecificExtension,
	mediumWithoutVendorSpecificExtension,
	maximumWithoutVendorSpecificExtension,
	...
}

TrafficLoadReductionIndication ::= INTEGER (1..99)

TransportLayerAddress ::= BIT STRING (SIZE(1..160, ...))

TypeOfError ::= ENUMERATED {
	not-understood,
	missing,
	...
}

TAIBasedMDT ::= SEQUENCE {
	tAIListforMDT			TAIListforMDT,
	iE-Extensions			ProtocolExtensionContainer { {TAIBasedMDT-ExtIEs} } OPTIONAL,
	...
}

TAIBasedMDT-ExtIEs NGAP-PROTOCOL-EXTENSION ::= {
	...
}

TAIListforMDT ::= SEQUENCE (SIZE(1..maxnoofTAforMDT)) OF TAI


TABasedMDT ::= SEQUENCE {
	tAListforMDT		TAListforMDT,
	iE-Extensions		ProtocolExtensionContainer { {TABasedMDT-ExtIEs} } OPTIONAL,
	...
}

TABasedMDT-ExtIEs NGAP-PROTOCOL-EXTENSION ::= {
	...
}

TAListforMDT ::= SEQUENCE (SIZE(1..maxnoofTAforMDT)) OF TAC

Threshold-RSRP ::= INTEGER(0..127)

Threshold-RSRQ ::= INTEGER(0..127)

Threshold-SINR ::= INTEGER(0..127)

TimeToTrigger ::= ENUMERATED {ms0, ms40, ms64, ms80, ms100, ms128, ms160, ms256, ms320, ms480, ms512, ms640, ms1024, ms1280, ms2560, ms5120}


TWAP-ID ::= OCTET STRING

TWIF-ID ::= CHOICE {
	tWIF-ID				 	BIT STRING (SIZE(32, ...)),
	choice-Extensions		ProtocolIE-SingleContainer { {TWIF-ID-ExtIEs} }
}

TWIF-ID-ExtIEs NGAP-PROTOCOL-IES ::= {
	...
}

TSCAssistanceInformation ::= SEQUENCE {
	periodicity				Periodicity,
	burstArrivalTime		BurstArrivalTime												OPTIONAL,
	iE-Extensions		ProtocolExtensionContainer { {TSCAssistanceInformation-ExtIEs} }	OPTIONAL,
	...
}

TSCAssistanceInformation-ExtIEs NGAP-PROTOCOL-EXTENSION ::= {
	...
}

TSCTrafficCharacteristics ::= SEQUENCE {
	tSCAssistanceInformationDL		TSCAssistanceInformation								OPTIONAL,
	tSCAssistanceInformationUL		TSCAssistanceInformation								OPTIONAL,
	iE-Extensions		ProtocolExtensionContainer { {TSCTrafficCharacteristics-ExtIEs} }	OPTIONAL,
	...
}

TSCTrafficCharacteristics-ExtIEs NGAP-PROTOCOL-EXTENSION ::= {
	...
}

-- U

UEAggregateMaximumBitRate ::= SEQUENCE {
	uEAggregateMaximumBitRateDL		BitRate,
	uEAggregateMaximumBitRateUL		BitRate,
	iE-Extensions		ProtocolExtensionContainer { {UEAggregateMaximumBitRate-ExtIEs} } OPTIONAL,
	...
}

UEAggregateMaximumBitRate-ExtIEs NGAP-PROTOCOL-EXTENSION ::= {
	...
}

UE-associatedLogicalNG-connectionList ::= SEQUENCE (SIZE(1..maxnoofNGConnectionsToReset)) OF UE-associatedLogicalNG-connectionItem

UE-associatedLogicalNG-connectionItem ::= SEQUENCE {
	aMF-UE-NGAP-ID		AMF-UE-NGAP-ID																		OPTIONAL,
	rAN-UE-NGAP-ID		RAN-UE-NGAP-ID																		OPTIONAL,
	iE-Extensions		ProtocolExtensionContainer { {UE-associatedLogicalNG-connectionItem-ExtIEs} }	OPTIONAL,
	...
}

UE-associatedLogicalNG-connectionItem-ExtIEs NGAP-PROTOCOL-EXTENSION ::= {
	...
}

UECapabilityInfoRequest ::= ENUMERATED {
	requested,
	...
}

UEContextRequest ::= ENUMERATED {requested, ...}


UEContextResumeRequestTransfer ::= SEQUENCE {
	qosFlowFailedToResumeList				QosFlowListWithCause									OPTIONAL,
	iE-Extensions		ProtocolExtensionContainer { {UEContextResumeRequestTransfer-ExtIEs} }		OPTIONAL,
	...
}

UEContextResumeRequestTransfer-ExtIEs NGAP-PROTOCOL-EXTENSION ::= {
	...
}

UEContextResumeResponseTransfer ::= SEQUENCE {
	qosFlowFailedToResumeList				QosFlowListWithCause									OPTIONAL,
	iE-Extensions		ProtocolExtensionContainer { {UEContextResumeResponseTransfer-ExtIEs} }		OPTIONAL,
	...
}

UEContextResumeResponseTransfer-ExtIEs NGAP-PROTOCOL-EXTENSION ::= {
	...
}

UEContextSuspendRequestTransfer ::= SEQUENCE {
	suspendIndicator				SuspendIndicator												OPTIONAL,
	iE-Extensions		ProtocolExtensionContainer { {UEContextSuspendRequestTransfer-ExtIEs} }		OPTIONAL,
	...
}

UEContextSuspendRequestTransfer-ExtIEs NGAP-PROTOCOL-EXTENSION ::= {
	...
}

UE-DifferentiationInfo ::= SEQUENCE {
	periodicCommunicationIndicator	ENUMERATED {periodically, ondemand, ... }			OPTIONAL,
	periodicTime					INTEGER (1..3600, ...)								OPTIONAL,
	scheduledCommunicationTime		ScheduledCommunicationTime 							OPTIONAL,
	stationaryIndication			ENUMERATED {stationary, mobile, ...}				OPTIONAL,
	trafficProfile					ENUMERATED {single-packet, dual-packets, multiple-packets, ...}	OPTIONAL,
	batteryIndication				ENUMERATED {battery-powered, battery-powered-not-rechargeable-or-replaceable, not-battery-powered, ...}		OPTIONAL,
	iE-Extensions		ProtocolExtensionContainer { { UE-DifferentiationInfo-ExtIEs} } OPTIONAL,
	...
}

UE-DifferentiationInfo-ExtIEs NGAP-PROTOCOL-EXTENSION ::= {
	...
}

UEHistoryInformation ::= SEQUENCE (SIZE(1..maxnoofCellsinUEHistoryInfo)) OF LastVisitedCellItem

UEHistoryInformationFromTheUE ::= CHOICE {
	nR						NRMobilityHistoryReport,
	choice-Extensions		ProtocolIE-SingleContainer { {UEHistoryInformationFromTheUE-ExtIEs} }
}

UEHistoryInformationFromTheUE-ExtIEs NGAP-PROTOCOL-IES ::= {
	...
}

UEIdentityIndexValue ::= CHOICE {
	indexLength10			BIT STRING (SIZE(10)),
	choice-Extensions		ProtocolIE-SingleContainer { {UEIdentityIndexValue-ExtIEs} }
}

UEIdentityIndexValue-ExtIEs NGAP-PROTOCOL-IES ::= {
	...
}

UE-NGAP-IDs ::= CHOICE {
	uE-NGAP-ID-pair		UE-NGAP-ID-pair,
	aMF-UE-NGAP-ID		AMF-UE-NGAP-ID,
	choice-Extensions		ProtocolIE-SingleContainer { {UE-NGAP-IDs-ExtIEs} }
}

UE-NGAP-IDs-ExtIEs NGAP-PROTOCOL-IES ::= {
	...
}

UE-NGAP-ID-pair ::= SEQUENCE{
	aMF-UE-NGAP-ID		AMF-UE-NGAP-ID,
	rAN-UE-NGAP-ID		RAN-UE-NGAP-ID,
	iE-Extensions		ProtocolExtensionContainer { {UE-NGAP-ID-pair-ExtIEs} } OPTIONAL,
	...
}

UE-NGAP-ID-pair-ExtIEs NGAP-PROTOCOL-EXTENSION ::= {
	...
}

UEPagingIdentity ::= CHOICE {
	fiveG-S-TMSI		FiveG-S-TMSI,
	choice-Extensions		ProtocolIE-SingleContainer { {UEPagingIdentity-ExtIEs} }
	}

UEPagingIdentity-ExtIEs NGAP-PROTOCOL-IES ::= {
	...
}

UEPresence ::= ENUMERATED {in, out, unknown, ...}

UEPresenceInAreaOfInterestList ::= SEQUENCE (SIZE(1..maxnoofAoI)) OF UEPresenceInAreaOfInterestItem

UEPresenceInAreaOfInterestItem ::= SEQUENCE {
	locationReportingReferenceID		LocationReportingReferenceID,
	uEPresence							UEPresence,
	iE-Extensions		ProtocolExtensionContainer { {UEPresenceInAreaOfInterestItem-ExtIEs} }	OPTIONAL,
	...
}

UEPresenceInAreaOfInterestItem-ExtIEs NGAP-PROTOCOL-EXTENSION ::= {
	...
}

UERadioCapability ::= OCTET STRING

UERadioCapabilityForPaging ::= SEQUENCE {
	uERadioCapabilityForPagingOfNR		UERadioCapabilityForPagingOfNR					OPTIONAL,
	uERadioCapabilityForPagingOfEUTRA		UERadioCapabilityForPagingOfEUTRA				OPTIONAL,
	iE-Extensions		ProtocolExtensionContainer { {UERadioCapabilityForPaging-ExtIEs} }	OPTIONAL,
	...
}

UERadioCapabilityForPaging-ExtIEs NGAP-PROTOCOL-EXTENSION ::= {
	{ ID id-UERadioCapabilityForPagingOfNB-IoT		CRITICALITY ignore	EXTENSION UERadioCapabilityForPagingOfNB-IoT		PRESENCE optional	},
	...
}

UERadioCapabilityForPagingOfNB-IoT ::= OCTET STRING

UERadioCapabilityForPagingOfNR ::= OCTET STRING

UERadioCapabilityForPagingOfEUTRA ::= OCTET STRING

UERadioCapabilityID ::= OCTET STRING

UERetentionInformation ::= ENUMERATED {
	ues-retained,
	...
}

UERLFReportContainer ::= CHOICE {
	nR			NRUERLFReportContainer,
	lTE			LTEUERLFReportContainer,
	choice-Extensions		ProtocolIE-SingleContainer { {UERLFReportContainer-ExtIEs} }
}

UERLFReportContainer-ExtIEs NGAP-PROTOCOL-IES ::= {
	...
}

UESecurityCapabilities ::= SEQUENCE {
	nRencryptionAlgorithms					NRencryptionAlgorithms,
	nRintegrityProtectionAlgorithms			NRintegrityProtectionAlgorithms,
	eUTRAencryptionAlgorithms				EUTRAencryptionAlgorithms,
	eUTRAintegrityProtectionAlgorithms		EUTRAintegrityProtectionAlgorithms,
	iE-Extensions		ProtocolExtensionContainer { {UESecurityCapabilities-ExtIEs} }	OPTIONAL,
	...
}

UESecurityCapabilities-ExtIEs NGAP-PROTOCOL-EXTENSION ::= {
	...
}

UE-UP-CIoT-Support ::= ENUMERATED {supported, ...}

UL-CP-SecurityInformation ::= SEQUENCE {
	ul-NAS-MAC				UL-NAS-MAC,
	ul-NAS-Count			UL-NAS-Count,
	iE-Extensions			ProtocolExtensionContainer { { UL-CP-SecurityInformation-ExtIEs} }	OPTIONAL,
	...
}

UL-CP-SecurityInformation-ExtIEs NGAP-PROTOCOL-EXTENSION ::= {
	...
}

UL-NAS-MAC ::= BIT STRING (SIZE (16))

UL-NAS-Count ::= BIT STRING (SIZE (5))

UL-NGU-UP-TNLModifyList ::= SEQUENCE (SIZE(1..maxnoofMultiConnectivity)) OF UL-NGU-UP-TNLModifyItem

UL-NGU-UP-TNLModifyItem ::= SEQUENCE {
	uL-NGU-UP-TNLInformation		UPTransportLayerInformation,
	dL-NGU-UP-TNLInformation		UPTransportLayerInformation,
	iE-Extensions		ProtocolExtensionContainer { {UL-NGU-UP-TNLModifyItem-ExtIEs} } OPTIONAL,
	...
}

UL-NGU-UP-TNLModifyItem-ExtIEs NGAP-PROTOCOL-EXTENSION ::= {
	{ ID id-RedundantUL-NGU-UP-TNLInformation	CRITICALITY ignore	EXTENSION UPTransportLayerInformation		PRESENCE optional	 	}|
	{ ID id-RedundantDL-NGU-UP-TNLInformation	CRITICALITY ignore	EXTENSION UPTransportLayerInformation		PRESENCE optional	 	},
	...
}

UnavailableGUAMIList ::= SEQUENCE (SIZE(1..maxnoofServedGUAMIs)) OF UnavailableGUAMIItem

UnavailableGUAMIItem ::= SEQUENCE {
	gUAMI								GUAMI,
	timerApproachForGUAMIRemoval		TimerApproachForGUAMIRemoval					OPTIONAL,
	backupAMFName						AMFName											OPTIONAL,
	iE-Extensions		ProtocolExtensionContainer { {UnavailableGUAMIItem-ExtIEs} }	OPTIONAL,
	...
}

UnavailableGUAMIItem-ExtIEs NGAP-PROTOCOL-EXTENSION ::= {
	...
}

ULForwarding ::= ENUMERATED {
	ul-forwarding-proposed,
	...
}

UpdateFeedback ::= BIT STRING (SIZE(8, ...))

UPTransportLayerInformation ::= CHOICE {
	gTPTunnel				GTPTunnel,
	choice-Extensions		ProtocolIE-SingleContainer { {UPTransportLayerInformation-ExtIEs} }
}

UPTransportLayerInformation-ExtIEs NGAP-PROTOCOL-IES ::= {
	...
}

UPTransportLayerInformationList ::= SEQUENCE (SIZE(1..maxnoofMultiConnectivityMinusOne)) OF UPTransportLayerInformationItem

UPTransportLayerInformationItem ::= SEQUENCE {
	nGU-UP-TNLInformation		UPTransportLayerInformation,
	iE-Extensions		ProtocolExtensionContainer { {UPTransportLayerInformationItem-ExtIEs} } OPTIONAL,
	...
}

UPTransportLayerInformationItem-ExtIEs NGAP-PROTOCOL-EXTENSION ::= {
	{ ID id-CommonNetworkInstance				CRITICALITY ignore	EXTENSION  CommonNetworkInstance						PRESENCE optional		},
	...
}


UPTransportLayerInformationPairList ::= SEQUENCE (SIZE(1..maxnoofMultiConnectivityMinusOne)) OF UPTransportLayerInformationPairItem

UPTransportLayerInformationPairItem ::= SEQUENCE {
	uL-NGU-UP-TNLInformation		UPTransportLayerInformation,
	dL-NGU-UP-TNLInformation		UPTransportLayerInformation,
	iE-Extensions		ProtocolExtensionContainer { {UPTransportLayerInformationPairItem-ExtIEs} } OPTIONAL,
	...
}

UPTransportLayerInformationPairItem-ExtIEs NGAP-PROTOCOL-EXTENSION ::= {
	...
}

URI-address ::= VisibleString

UserLocationInformation ::= CHOICE {
	userLocationInformationEUTRA	UserLocationInformationEUTRA,
	userLocationInformationNR		UserLocationInformationNR,
	userLocationInformationN3IWF	UserLocationInformationN3IWF,
	choice-Extensions		ProtocolIE-SingleContainer { {UserLocationInformation-ExtIEs} }
}

UserLocationInformation-ExtIEs NGAP-PROTOCOL-IES ::= {
	{ ID id-UserLocationInformationTNGF		CRITICALITY ignore	TYPE UserLocationInformationTNGF		PRESENCE mandatory	}|
	{ ID id-UserLocationInformationTWIF		CRITICALITY ignore	TYPE UserLocationInformationTWIF		PRESENCE mandatory	}|
	{ ID id-UserLocationInformationW-AGF	CRITICALITY ignore	TYPE UserLocationInformationW-AGF		PRESENCE mandatory	},
	...
}

UserLocationInformationEUTRA ::= SEQUENCE {
	eUTRA-CGI			EUTRA-CGI,
	tAI					TAI,
	timeStamp			TimeStamp																OPTIONAL,
	iE-Extensions		ProtocolExtensionContainer { {UserLocationInformationEUTRA-ExtIEs} }	OPTIONAL,
	...
}

UserLocationInformationEUTRA-ExtIEs NGAP-PROTOCOL-EXTENSION ::= {
	{ ID id-PSCellInformation	CRITICALITY ignore	EXTENSION NGRAN-CGI				PRESENCE optional},
	...
}

UserLocationInformationN3IWF ::= SEQUENCE {
	iPAddress			TransportLayerAddress,
	portNumber			PortNumber,
	iE-Extensions		ProtocolExtensionContainer { {UserLocationInformationN3IWF-ExtIEs} }	OPTIONAL,
	...
}

UserLocationInformationN3IWF-ExtIEs NGAP-PROTOCOL-EXTENSION ::= {
	...
}

UserLocationInformationTNGF ::= SEQUENCE {
	tNAP-ID				TNAP-ID,
	iPAddress			TransportLayerAddress,
	portNumber			PortNumber															OPTIONAL,
	iE-Extensions		ProtocolExtensionContainer { {UserLocationInformationTNGF-ExtIEs} }	OPTIONAL,
	...
}

UserLocationInformationTNGF-ExtIEs NGAP-PROTOCOL-EXTENSION ::= {
	...
}

UserLocationInformationTWIF ::= SEQUENCE {
	tWAP-ID				TWAP-ID,
	iPAddress			TransportLayerAddress,
	portNumber			PortNumber															OPTIONAL,
	iE-Extensions		ProtocolExtensionContainer { {UserLocationInformationTWIF-ExtIEs} }	OPTIONAL,
	...
}

UserLocationInformationTWIF-ExtIEs NGAP-PROTOCOL-EXTENSION ::= {
	...
}

UserLocationInformationW-AGF ::= CHOICE {
	globalLine-ID	GlobalLine-ID,
	hFCNode-ID		HFCNode-ID,
	choice-Extensions		ProtocolIE-SingleContainer { { UserLocationInformationW-AGF-ExtIEs} }
}

UserLocationInformationW-AGF-ExtIEs NGAP-PROTOCOL-IES ::= {
	{ ID id-GlobalCable-ID 	CRITICALITY 	ignore 	TYPE 	GlobalCable-ID 	PRESENCE 	mandatory },
	...
}

UserLocationInformationNR ::= SEQUENCE {
	nR-CGI				NR-CGI,
	tAI					TAI,
	timeStamp			TimeStamp															OPTIONAL,
	iE-Extensions		ProtocolExtensionContainer { {UserLocationInformationNR-ExtIEs} }	OPTIONAL,
	...
}

UserLocationInformationNR-ExtIEs NGAP-PROTOCOL-EXTENSION ::= {
	{ ID id-PSCellInformation	CRITICALITY ignore	EXTENSION NGRAN-CGI		PRESENCE optional	}|
	{ ID id-NID					CRITICALITY reject	EXTENSION NID			PRESENCE optional	},
	...
}

UserPlaneSecurityInformation ::= SEQUENCE {
	securityResult			SecurityResult,
	securityIndication		SecurityIndication,
	iE-Extensions		ProtocolExtensionContainer { {UserPlaneSecurityInformation-ExtIEs} }	OPTIONAL,
	...
}

UserPlaneSecurityInformation-ExtIEs NGAP-PROTOCOL-EXTENSION ::= {
	...
}

-- V

VolumeTimedReportList ::= SEQUENCE (SIZE(1..maxnoofTimePeriods)) OF VolumeTimedReport-Item

VolumeTimedReport-Item ::= SEQUENCE {
	startTimeStamp				OCTET STRING (SIZE(4)),
	endTimeStamp				OCTET STRING (SIZE(4)),
	usageCountUL				INTEGER (0..18446744073709551615),
	usageCountDL				INTEGER (0..18446744073709551615),
	iE-Extensions		ProtocolExtensionContainer { {VolumeTimedReport-Item-ExtIEs} } OPTIONAL,
	...
}

VolumeTimedReport-Item-ExtIEs NGAP-PROTOCOL-EXTENSION ::= {
	...
}

-- W

W-AGF-ID ::= CHOICE {
	w-AGF-ID				BIT STRING (SIZE(16, ...)),
	choice-Extensions		ProtocolIE-SingleContainer { {W-AGF-ID-ExtIEs} }
}

W-AGF-ID-ExtIEs NGAP-PROTOCOL-IES ::= {
	...
}

WarningAreaCoordinates ::= OCTET STRING (SIZE(1..1024))

WarningAreaList ::= CHOICE {
	eUTRA-CGIListForWarning			EUTRA-CGIListForWarning,
	nR-CGIListForWarning			NR-CGIListForWarning,
	tAIListForWarning				TAIListForWarning,
	emergencyAreaIDList				EmergencyAreaIDList,
	choice-Extensions		ProtocolIE-SingleContainer { {WarningAreaList-ExtIEs} }
}

WarningAreaList-ExtIEs NGAP-PROTOCOL-IES ::= {
	...
}

WarningMessageContents ::= OCTET STRING (SIZE(1..9600))

WarningSecurityInfo ::= OCTET STRING (SIZE(50))

WarningType ::= OCTET STRING (SIZE(2))

WLANMeasurementConfiguration ::= SEQUENCE {
	wlanMeasConfig             	WLANMeasConfig,
	wlanMeasConfigNameList		WLANMeasConfigNameList            								OPTIONAL,
	wlan-rssi                  	ENUMERATED {true, ...}            								OPTIONAL,
	wlan-rtt                   	ENUMERATED {true, ...}            								OPTIONAL,
	iE-Extensions		ProtocolExtensionContainer { { WLANMeasurementConfiguration-ExtIEs } } 	OPTIONAL,
	...
}

WLANMeasurementConfiguration-ExtIEs NGAP-PROTOCOL-EXTENSION ::= {
	...
}

WLANMeasConfigNameList ::= SEQUENCE (SIZE(1..maxnoofWLANName)) OF WLANMeasConfigNameItem

WLANMeasConfigNameItem ::= SEQUENCE {
	wLANName			WLANName,
	iE-Extensions		ProtocolExtensionContainer { { WLANMeasConfigNameItem-ExtIEs } } 	OPTIONAL,
	...
}

WLANMeasConfigNameItem-ExtIEs NGAP-PROTOCOL-EXTENSION ::= {
	...
}

WLANMeasConfig::= ENUMERATED {setup,...}

WLANName ::= OCTET STRING (SIZE (1..32))   

WUS-Assistance-Information  ::= SEQUENCE {
	pagingProbabilityInformation             PagingProbabilityInformation,
	iE-Extensions		ProtocolExtensionContainer { { WUS-Assistance-Information-ExtIEs } } OPTIONAL,
	...
}

WUS-Assistance-Information-ExtIEs NGAP-PROTOCOL-EXTENSION ::= {
	...
}

-- X

XnExtTLAs ::= SEQUENCE (SIZE(1..maxnoofXnExtTLAs)) OF XnExtTLA-Item

XnExtTLA-Item ::= SEQUENCE {
	iPsecTLA					TransportLayerAddress							OPTIONAL,
	gTP-TLAs					XnGTP-TLAs										OPTIONAL,
	iE-Extensions		ProtocolExtensionContainer { {XnExtTLA-Item-ExtIEs} } 	OPTIONAL,
	...
}

XnExtTLA-Item-ExtIEs NGAP-PROTOCOL-EXTENSION ::= {
	{ ID id-SCTP-TLAs		CRITICALITY ignore	EXTENSION SCTP-TLAs		PRESENCE optional },
	...
}

XnGTP-TLAs ::= SEQUENCE (SIZE(1..maxnoofXnGTP-TLAs)) OF TransportLayerAddress

XnTLAs ::= SEQUENCE (SIZE(1..maxnoofXnTLAs)) OF TransportLayerAddress

XnTNLConfigurationInfo ::= SEQUENCE {
	xnTransportLayerAddresses			XnTLAs,
	xnExtendedTransportLayerAddresses	XnExtTLAs										OPTIONAL,
	iE-Extensions		ProtocolExtensionContainer { {XnTNLConfigurationInfo-ExtIEs} }	OPTIONAL,
	...
}

XnTNLConfigurationInfo-ExtIEs NGAP-PROTOCOL-EXTENSION ::= {
	...
}

-- Y
-- Z

END
-- ASN1STOP

-- ASN1START
-- **************************************************************
--
-- Common definitions
--
-- **************************************************************

NGAP-CommonDataTypes {
itu-t (0) identified-organization (4) etsi (0) mobileDomain (0) 
ngran-Access (22) modules (3) ngap (1) version1 (1) ngap-CommonDataTypes (3) }

DEFINITIONS AUTOMATIC TAGS ::= 

BEGIN

Criticality		::= ENUMERATED { reject, ignore, notify }

Presence		::= ENUMERATED { optional, conditional, mandatory }

PrivateIE-ID	::= CHOICE {
	local				INTEGER (0..65535),
	global				OBJECT IDENTIFIER
}

ProcedureCode		::= INTEGER (0..255)

ProtocolExtensionID	::= INTEGER (0..65535)

ProtocolIE-ID		::= INTEGER (0..65535)

TriggeringMessage	::= ENUMERATED { initiating-message, successful-outcome, unsuccessfull-outcome }

END
-- ASN1STOP

-- ASN1START
-- **************************************************************
--
-- Constant definitions
--
-- **************************************************************

NGAP-Constants { 
itu-t (0) identified-organization (4) etsi (0) mobileDomain (0) 
ngran-Access (22) modules (3) ngap (1) version1 (1) ngap-Constants (4) } 

DEFINITIONS AUTOMATIC TAGS ::= 

BEGIN

-- **************************************************************
--
-- IE parameter types from other modules.
--
-- **************************************************************

IMPORTS

	ProcedureCode,
	ProtocolIE-ID
FROM NGAP-CommonDataTypes;


-- **************************************************************
--
-- Elementary Procedures
--
-- **************************************************************

id-AMFConfigurationUpdate					ProcedureCode ::= 0
id-AMFStatusIndication						ProcedureCode ::= 1
id-CellTrafficTrace							ProcedureCode ::= 2
id-DeactivateTrace							ProcedureCode ::= 3
id-DownlinkNASTransport						ProcedureCode ::= 4
id-DownlinkNonUEAssociatedNRPPaTransport	ProcedureCode ::= 5
id-DownlinkRANConfigurationTransfer			ProcedureCode ::= 6
id-DownlinkRANStatusTransfer				ProcedureCode ::= 7
id-DownlinkUEAssociatedNRPPaTransport		ProcedureCode ::= 8
id-ErrorIndication							ProcedureCode ::= 9
id-HandoverCancel							ProcedureCode ::= 10
id-HandoverNotification						ProcedureCode ::= 11
id-HandoverPreparation						ProcedureCode ::= 12
id-HandoverResourceAllocation				ProcedureCode ::= 13
id-InitialContextSetup						ProcedureCode ::= 14
id-InitialUEMessage							ProcedureCode ::= 15
id-LocationReportingControl					ProcedureCode ::= 16
id-LocationReportingFailureIndication		ProcedureCode ::= 17
id-LocationReport							ProcedureCode ::= 18
id-NASNonDeliveryIndication					ProcedureCode ::= 19
id-NGReset									ProcedureCode ::= 20
id-NGSetup									ProcedureCode ::= 21
id-OverloadStart							ProcedureCode ::= 22
id-OverloadStop								ProcedureCode ::= 23
id-Paging									ProcedureCode ::= 24
id-PathSwitchRequest						ProcedureCode ::= 25
id-PDUSessionResourceModify					ProcedureCode ::= 26
id-PDUSessionResourceModifyIndication		ProcedureCode ::= 27
id-PDUSessionResourceRelease				ProcedureCode ::= 28
id-PDUSessionResourceSetup					ProcedureCode ::= 29
id-PDUSessionResourceNotify					ProcedureCode ::= 30
id-PrivateMessage							ProcedureCode ::= 31
id-PWSCancel								ProcedureCode ::= 32
id-PWSFailureIndication						ProcedureCode ::= 33
id-PWSRestartIndication						ProcedureCode ::= 34
id-RANConfigurationUpdate					ProcedureCode ::= 35
id-RerouteNASRequest						ProcedureCode ::= 36
id-RRCInactiveTransitionReport				ProcedureCode ::= 37
id-TraceFailureIndication					ProcedureCode ::= 38
id-TraceStart								ProcedureCode ::= 39
id-UEContextModification					ProcedureCode ::= 40
id-UEContextRelease							ProcedureCode ::= 41
id-UEContextReleaseRequest					ProcedureCode ::= 42
id-UERadioCapabilityCheck					ProcedureCode ::= 43
id-UERadioCapabilityInfoIndication			ProcedureCode ::= 44
id-UETNLABindingRelease						ProcedureCode ::= 45
id-UplinkNASTransport						ProcedureCode ::= 46
id-UplinkNonUEAssociatedNRPPaTransport		ProcedureCode ::= 47
id-UplinkRANConfigurationTransfer			ProcedureCode ::= 48
id-UplinkRANStatusTransfer					ProcedureCode ::= 49
id-UplinkUEAssociatedNRPPaTransport			ProcedureCode ::= 50
id-WriteReplaceWarning						ProcedureCode ::= 51
id-SecondaryRATDataUsageReport				ProcedureCode ::= 52
id-UplinkRIMInformationTransfer				ProcedureCode ::= 53
id-DownlinkRIMInformationTransfer			ProcedureCode ::= 54
id-RetrieveUEInformation					ProcedureCode ::= 55
id-UEInformationTransfer					ProcedureCode ::= 56
id-RANCPRelocationIndication				ProcedureCode ::= 57
id-UEContextResume							ProcedureCode ::= 58
id-UEContextSuspend							ProcedureCode ::= 59
id-UERadioCapabilityIDMapping				ProcedureCode ::= 60
id-HandoverSuccess							ProcedureCode ::= 61
id-UplinkRANEarlyStatusTransfer				ProcedureCode ::= 62
id-DownlinkRANEarlyStatusTransfer			ProcedureCode ::= 63
id-AMFCPRelocationIndication				ProcedureCode ::= 64
id-ConnectionEstablishmentIndication		ProcedureCode ::= 65

-- **************************************************************
--
-- Extension constants
--
-- **************************************************************

maxPrivateIEs							INTEGER ::= 65535
maxProtocolExtensions					INTEGER ::= 65535
maxProtocolIEs							INTEGER ::= 65535

-- **************************************************************
--
-- Lists
--
-- **************************************************************

	maxnoofAllowedAreas					INTEGER ::= 16
	maxnoofAllowedCAGsperPLMN			INTEGER ::= 256
	maxnoofAllowedS-NSSAIs				INTEGER ::= 8
	maxnoofBluetoothName				INTEGER ::= 4
	maxnoofBPLMNs						INTEGER ::= 12
	maxnoofCAGSperCell					INTEGER ::= 64
	maxnoofCellIDforMDT					INTEGER ::= 32
	maxnoofCellIDforWarning				INTEGER ::= 65535
	maxnoofCellinAoI					INTEGER ::= 256
	maxnoofCellinEAI					INTEGER ::= 65535
	maxnoofCellinTAI					INTEGER ::= 65535
	maxnoofCellsingNB					INTEGER ::= 16384
	maxnoofCellsinngeNB					INTEGER ::= 256
	maxnoofCellsinUEHistoryInfo			INTEGER ::= 16
	maxnoofCellsUEMovingTrajectory		INTEGER ::= 16
	maxnoofDRBs							INTEGER ::= 32
	maxnoofEmergencyAreaID				INTEGER ::= 65535
	maxnoofEAIforRestart				INTEGER ::= 256
	maxnoofEPLMNs						INTEGER ::= 15
	maxnoofEPLMNsPlusOne				INTEGER ::= 16
	maxnoofE-RABs						INTEGER ::= 256
	maxnoofErrors						INTEGER ::= 256
	maxnoofExtSliceItems					INTEGER ::= 65535
	maxnoofForbTACs						INTEGER ::= 4096
	maxnoofFreqforMDT					INTEGER ::= 8
	maxnoofMDTPLMNs						INTEGER ::= 16
	maxnoofMultiConnectivity			INTEGER ::= 4
	maxnoofMultiConnectivityMinusOne	INTEGER ::= 3
	maxnoofNeighPCIforMDT				INTEGER ::= 32
	maxnoofNGConnectionsToReset			INTEGER ::= 65536
	maxnoofNRCellBands					INTEGER ::= 32
	maxnoofPC5QoSFlows 					INTEGER ::= 2048
	maxnoofPDUSessions					INTEGER ::= 256
	maxnoofPLMNs						INTEGER ::= 12
	maxnoofQosFlows						INTEGER ::= 64
	maxnoofQosParaSets					INTEGER ::= 8
	maxnoofRANNodeinAoI					INTEGER ::= 64
	maxnoofRecommendedCells				INTEGER ::= 16
	maxnoofRecommendedRANNodes			INTEGER ::= 16
	maxnoofAoI							INTEGER ::= 64
	maxnoofSensorName					INTEGER ::= 3
	maxnoofServedGUAMIs					INTEGER ::= 256
	maxnoofSliceItems					INTEGER ::= 1024
	maxnoofTACs							INTEGER ::= 256
	maxnoofTAforMDT						INTEGER ::= 8
	maxnoofTAIforInactive				INTEGER ::= 16
	maxnoofTAIforPaging					INTEGER ::= 16
	maxnoofTAIforRestart				INTEGER ::= 2048
	maxnoofTAIforWarning				INTEGER ::= 65535
	maxnoofTAIinAoI						INTEGER ::= 16
	maxnoofTimePeriods					INTEGER ::= 2
	maxnoofTNLAssociations				INTEGER ::= 32
	maxnoofWLANName						INTEGER ::= 4
	maxnoofXnExtTLAs					INTEGER ::= 16
	maxnoofXnGTP-TLAs					INTEGER ::= 16
	maxnoofXnTLAs						INTEGER ::= 2
	maxnoofCandidateCells				INTEGER ::= 32
	maxNRARFCN							INTEGER ::= 3279165

-- **************************************************************
--
-- IEs
--
-- **************************************************************

	id-AllowedNSSAI											ProtocolIE-ID ::= 0
	id-AMFName												ProtocolIE-ID ::= 1
	id-AMFOverloadResponse									ProtocolIE-ID ::= 2
	id-AMFSetID												ProtocolIE-ID ::= 3
	id-AMF-TNLAssociationFailedToSetupList					ProtocolIE-ID ::= 4
	id-AMF-TNLAssociationSetupList							ProtocolIE-ID ::= 5
	id-AMF-TNLAssociationToAddList							ProtocolIE-ID ::= 6
	id-AMF-TNLAssociationToRemoveList						ProtocolIE-ID ::= 7
	id-AMF-TNLAssociationToUpdateList						ProtocolIE-ID ::= 8
	id-AMFTrafficLoadReductionIndication					ProtocolIE-ID ::= 9
	id-AMF-UE-NGAP-ID										ProtocolIE-ID ::= 10
	id-AssistanceDataForPaging								ProtocolIE-ID ::= 11
	id-BroadcastCancelledAreaList							ProtocolIE-ID ::= 12
	id-BroadcastCompletedAreaList							ProtocolIE-ID ::= 13
	id-CancelAllWarningMessages								ProtocolIE-ID ::= 14
	id-Cause												ProtocolIE-ID ::= 15
	id-CellIDListForRestart									ProtocolIE-ID ::= 16
	id-ConcurrentWarningMessageInd							ProtocolIE-ID ::= 17
	id-CoreNetworkAssistanceInformationForInactive			ProtocolIE-ID ::= 18
	id-CriticalityDiagnostics								ProtocolIE-ID ::= 19
	id-DataCodingScheme										ProtocolIE-ID ::= 20
	id-DefaultPagingDRX										ProtocolIE-ID ::= 21
	id-DirectForwardingPathAvailability						ProtocolIE-ID ::= 22
	id-EmergencyAreaIDListForRestart						ProtocolIE-ID ::= 23
	id-EmergencyFallbackIndicator							ProtocolIE-ID ::= 24
	id-EUTRA-CGI											ProtocolIE-ID ::= 25
	id-FiveG-S-TMSI											ProtocolIE-ID ::= 26
	id-GlobalRANNodeID										ProtocolIE-ID ::= 27
	id-GUAMI												ProtocolIE-ID ::= 28
	id-HandoverType											ProtocolIE-ID ::= 29
	id-IMSVoiceSupportIndicator								ProtocolIE-ID ::= 30
	id-IndexToRFSP											ProtocolIE-ID ::= 31
	id-InfoOnRecommendedCellsAndRANNodesForPaging			ProtocolIE-ID ::= 32
	id-LocationReportingRequestType							ProtocolIE-ID ::= 33
	id-MaskedIMEISV											ProtocolIE-ID ::= 34
	id-MessageIdentifier									ProtocolIE-ID ::= 35
	id-MobilityRestrictionList								ProtocolIE-ID ::= 36
	id-NASC													ProtocolIE-ID ::= 37
	id-NAS-PDU												ProtocolIE-ID ::= 38
	id-NASSecurityParametersFromNGRAN						ProtocolIE-ID ::= 39
	id-NewAMF-UE-NGAP-ID									ProtocolIE-ID ::= 40
	id-NewSecurityContextInd								ProtocolIE-ID ::= 41
	id-NGAP-Message											ProtocolIE-ID ::= 42
	id-NGRAN-CGI											ProtocolIE-ID ::= 43
	id-NGRANTraceID											ProtocolIE-ID ::= 44
	id-NR-CGI												ProtocolIE-ID ::= 45
	id-NRPPa-PDU											ProtocolIE-ID ::= 46
	id-NumberOfBroadcastsRequested							ProtocolIE-ID ::= 47
	id-OldAMF												ProtocolIE-ID ::= 48
	id-OverloadStartNSSAIList								ProtocolIE-ID ::= 49
	id-PagingDRX											ProtocolIE-ID ::= 50
	id-PagingOrigin											ProtocolIE-ID ::= 51
	id-PagingPriority										ProtocolIE-ID ::= 52
	id-PDUSessionResourceAdmittedList						ProtocolIE-ID ::= 53
	id-PDUSessionResourceFailedToModifyListModRes			ProtocolIE-ID ::= 54
	id-PDUSessionResourceFailedToSetupListCxtRes			ProtocolIE-ID ::= 55
	id-PDUSessionResourceFailedToSetupListHOAck				ProtocolIE-ID ::= 56
	id-PDUSessionResourceFailedToSetupListPSReq				ProtocolIE-ID ::= 57
	id-PDUSessionResourceFailedToSetupListSURes				ProtocolIE-ID ::= 58
	id-PDUSessionResourceHandoverList						ProtocolIE-ID ::= 59
	id-PDUSessionResourceListCxtRelCpl						ProtocolIE-ID ::= 60
	id-PDUSessionResourceListHORqd							ProtocolIE-ID ::= 61
	id-PDUSessionResourceModifyListModCfm					ProtocolIE-ID ::= 62
	id-PDUSessionResourceModifyListModInd					ProtocolIE-ID ::= 63
	id-PDUSessionResourceModifyListModReq					ProtocolIE-ID ::= 64
	id-PDUSessionResourceModifyListModRes					ProtocolIE-ID ::= 65
	id-PDUSessionResourceNotifyList							ProtocolIE-ID ::= 66
	id-PDUSessionResourceReleasedListNot					ProtocolIE-ID ::= 67
	id-PDUSessionResourceReleasedListPSAck					ProtocolIE-ID ::= 68
	id-PDUSessionResourceReleasedListPSFail					ProtocolIE-ID ::= 69
	id-PDUSessionResourceReleasedListRelRes					ProtocolIE-ID ::= 70
	id-PDUSessionResourceSetupListCxtReq					ProtocolIE-ID ::= 71
	id-PDUSessionResourceSetupListCxtRes					ProtocolIE-ID ::= 72
	id-PDUSessionResourceSetupListHOReq						ProtocolIE-ID ::= 73
	id-PDUSessionResourceSetupListSUReq						ProtocolIE-ID ::= 74
	id-PDUSessionResourceSetupListSURes						ProtocolIE-ID ::= 75
	id-PDUSessionResourceToBeSwitchedDLList					ProtocolIE-ID ::= 76
	id-PDUSessionResourceSwitchedList						ProtocolIE-ID ::= 77
	id-PDUSessionResourceToReleaseListHOCmd					ProtocolIE-ID ::= 78
	id-PDUSessionResourceToReleaseListRelCmd				ProtocolIE-ID ::= 79
	id-PLMNSupportList										ProtocolIE-ID ::= 80
	id-PWSFailedCellIDList									ProtocolIE-ID ::= 81
	id-RANNodeName											ProtocolIE-ID ::= 82
	id-RANPagingPriority									ProtocolIE-ID ::= 83
	id-RANStatusTransfer-TransparentContainer				ProtocolIE-ID ::= 84
	id-RAN-UE-NGAP-ID										ProtocolIE-ID ::= 85
	id-RelativeAMFCapacity									ProtocolIE-ID ::= 86
	id-RepetitionPeriod										ProtocolIE-ID ::= 87
	id-ResetType											ProtocolIE-ID ::= 88
	id-RoutingID											ProtocolIE-ID ::= 89
	id-RRCEstablishmentCause								ProtocolIE-ID ::= 90
	id-RRCInactiveTransitionReportRequest					ProtocolIE-ID ::= 91
	id-RRCState												ProtocolIE-ID ::= 92
	id-SecurityContext										ProtocolIE-ID ::= 93
	id-SecurityKey											ProtocolIE-ID ::= 94
	id-SerialNumber											ProtocolIE-ID ::= 95
	id-ServedGUAMIList										ProtocolIE-ID ::= 96
	id-SliceSupportList										ProtocolIE-ID ::= 97
	id-SONConfigurationTransferDL							ProtocolIE-ID ::= 98
	id-SONConfigurationTransferUL							ProtocolIE-ID ::= 99
	id-SourceAMF-UE-NGAP-ID									ProtocolIE-ID ::= 100
	id-SourceToTarget-TransparentContainer					ProtocolIE-ID ::= 101
	id-SupportedTAList										ProtocolIE-ID ::= 102
	id-TAIListForPaging										ProtocolIE-ID ::= 103
	id-TAIListForRestart									ProtocolIE-ID ::= 104
	id-TargetID												ProtocolIE-ID ::= 105
	id-TargetToSource-TransparentContainer					ProtocolIE-ID ::= 106
	id-TimeToWait											ProtocolIE-ID ::= 107
	id-TraceActivation										ProtocolIE-ID ::= 108
	id-TraceCollectionEntityIPAddress						ProtocolIE-ID ::= 109
	id-UEAggregateMaximumBitRate							ProtocolIE-ID ::= 110
	id-UE-associatedLogicalNG-connectionList				ProtocolIE-ID ::= 111
	id-UEContextRequest										ProtocolIE-ID ::= 112
	id-UE-NGAP-IDs											ProtocolIE-ID ::= 114
	id-UEPagingIdentity										ProtocolIE-ID ::= 115
	id-UEPresenceInAreaOfInterestList						ProtocolIE-ID ::= 116
	id-UERadioCapability									ProtocolIE-ID ::= 117
	id-UERadioCapabilityForPaging							ProtocolIE-ID ::= 118
	id-UESecurityCapabilities								ProtocolIE-ID ::= 119
	id-UnavailableGUAMIList									ProtocolIE-ID ::= 120
	id-UserLocationInformation								ProtocolIE-ID ::= 121
	id-WarningAreaList										ProtocolIE-ID ::= 122
	id-WarningMessageContents								ProtocolIE-ID ::= 123
	id-WarningSecurityInfo									ProtocolIE-ID ::= 124
	id-WarningType											ProtocolIE-ID ::= 125
	id-AdditionalUL-NGU-UP-TNLInformation					ProtocolIE-ID ::= 126
	id-DataForwardingNotPossible							ProtocolIE-ID ::= 127
	id-DL-NGU-UP-TNLInformation								ProtocolIE-ID ::= 128
	id-NetworkInstance										ProtocolIE-ID ::= 129
	id-PDUSessionAggregateMaximumBitRate					ProtocolIE-ID ::= 130
	id-PDUSessionResourceFailedToModifyListModCfm			ProtocolIE-ID ::= 131
	id-PDUSessionResourceFailedToSetupListCxtFail			ProtocolIE-ID ::= 132
	id-PDUSessionResourceListCxtRelReq						ProtocolIE-ID ::= 133
	id-PDUSessionType										ProtocolIE-ID ::= 134
	id-QosFlowAddOrModifyRequestList						ProtocolIE-ID ::= 135
	id-QosFlowSetupRequestList								ProtocolIE-ID ::= 136
	id-QosFlowToReleaseList									ProtocolIE-ID ::= 137
	id-SecurityIndication									ProtocolIE-ID ::= 138
	id-UL-NGU-UP-TNLInformation								ProtocolIE-ID ::= 139
	id-UL-NGU-UP-TNLModifyList								ProtocolIE-ID ::= 140
	id-WarningAreaCoordinates								ProtocolIE-ID ::= 141
	id-PDUSessionResourceSecondaryRATUsageList				ProtocolIE-ID ::= 142
	id-HandoverFlag											ProtocolIE-ID ::= 143
	id-SecondaryRATUsageInformation							ProtocolIE-ID ::= 144
	id-PDUSessionResourceReleaseResponseTransfer			ProtocolIE-ID ::= 145
	id-RedirectionVoiceFallback								ProtocolIE-ID ::= 146
	id-UERetentionInformation								ProtocolIE-ID ::= 147
	id-S-NSSAI												ProtocolIE-ID ::= 148
	id-PSCellInformation									ProtocolIE-ID ::= 149
	id-LastEUTRAN-PLMNIdentity								ProtocolIE-ID ::= 150
	id-MaximumIntegrityProtectedDataRate-DL					ProtocolIE-ID ::= 151
	id-AdditionalDLForwardingUPTNLInformation				ProtocolIE-ID ::= 152
	id-AdditionalDLUPTNLInformationForHOList				ProtocolIE-ID ::= 153
	id-AdditionalNGU-UP-TNLInformation						ProtocolIE-ID ::= 154
	id-AdditionalDLQosFlowPerTNLInformation					ProtocolIE-ID ::= 155
	id-SecurityResult										ProtocolIE-ID ::= 156
	id-ENDC-SONConfigurationTransferDL						ProtocolIE-ID ::= 157
	id-ENDC-SONConfigurationTransferUL						ProtocolIE-ID ::= 158
	id-OldAssociatedQosFlowList-ULendmarkerexpected			ProtocolIE-ID ::= 159
	id-CNTypeRestrictionsForEquivalent						ProtocolIE-ID ::= 160
	id-CNTypeRestrictionsForServing							ProtocolIE-ID ::= 161
	id-NewGUAMI												ProtocolIE-ID ::= 162
	id-ULForwarding											ProtocolIE-ID ::= 163
	id-ULForwardingUP-TNLInformation						ProtocolIE-ID ::= 164
	id-CNAssistedRANTuning									ProtocolIE-ID ::= 165
	id-CommonNetworkInstance								ProtocolIE-ID ::= 166
	id-NGRAN-TNLAssociationToRemoveList						ProtocolIE-ID ::= 167
	id-TNLAssociationTransportLayerAddressNGRAN				ProtocolIE-ID ::= 168
	id-EndpointIPAddressAndPort								ProtocolIE-ID ::= 169
	id-LocationReportingAdditionalInfo						ProtocolIE-ID ::= 170
	id-SourceToTarget-AMFInformationReroute					ProtocolIE-ID ::= 171
	id-AdditionalULForwardingUPTNLInformation				ProtocolIE-ID ::= 172
	id-SCTP-TLAs											ProtocolIE-ID ::= 173
	id-SelectedPLMNIdentity									ProtocolIE-ID ::= 174
	id-RIMInformationTransfer								ProtocolIE-ID ::= 175
	id-GUAMIType											ProtocolIE-ID ::= 176
	id-SRVCCOperationPossible								ProtocolIE-ID ::= 177
	id-TargetRNC-ID											ProtocolIE-ID ::= 178
	id-RAT-Information										ProtocolIE-ID ::= 179
	id-ExtendedRATRestrictionInformation					ProtocolIE-ID ::= 180
	id-QosMonitoringRequest									ProtocolIE-ID ::= 181
	id-SgNB-UE-X2AP-ID										ProtocolIE-ID ::= 182
	id-AdditionalRedundantDL-NGU-UP-TNLInformation			ProtocolIE-ID ::= 183
	id-AdditionalRedundantDLQosFlowPerTNLInformation		ProtocolIE-ID ::= 184
	id-AdditionalRedundantNGU-UP-TNLInformation				ProtocolIE-ID ::= 185
	id-AdditionalRedundantUL-NGU-UP-TNLInformation			ProtocolIE-ID ::= 186
	id-CNPacketDelayBudgetDL								ProtocolIE-ID ::= 187
	id-CNPacketDelayBudgetUL								ProtocolIE-ID ::= 188
	id-ExtendedPacketDelayBudget							ProtocolIE-ID ::= 189
	id-RedundantCommonNetworkInstance						ProtocolIE-ID ::= 190
	id-RedundantDL-NGU-TNLInformationReused					ProtocolIE-ID ::= 191
	id-RedundantDL-NGU-UP-TNLInformation					ProtocolIE-ID ::= 192
	id-RedundantDLQosFlowPerTNLInformation					ProtocolIE-ID ::= 193
	id-RedundantQosFlowIndicator							ProtocolIE-ID ::= 194
	id-RedundantUL-NGU-UP-TNLInformation					ProtocolIE-ID ::= 195
	id-TSCTrafficCharacteristics							ProtocolIE-ID ::= 196
	id-RedundantPDUSessionInformation 						ProtocolIE-ID ::= 197
	id-UsedRSNInformation									ProtocolIE-ID ::= 198
	id-IAB-Authorized										ProtocolIE-ID ::= 199
	id-IAB-Supported										ProtocolIE-ID ::= 200
	id-IABNodeIndication									ProtocolIE-ID ::= 201
	id-NB-IoT-PagingDRX										ProtocolIE-ID ::= 202
	id-NB-IoT-Paging-eDRXInfo								ProtocolIE-ID ::= 203
	id-NB-IoT-DefaultPagingDRX								ProtocolIE-ID ::= 204
	id-Enhanced-CoverageRestriction							ProtocolIE-ID ::= 205
	id-Extended-ConnectedTime								ProtocolIE-ID ::= 206
	id-PagingAssisDataforCEcapabUE							ProtocolIE-ID ::= 207
	id-WUS-Assistance-Information							ProtocolIE-ID ::= 208
	id-UE-DifferentiationInfo								ProtocolIE-ID ::= 209
	id-NB-IoT-UEPriority									ProtocolIE-ID ::= 210
	id-UL-CP-SecurityInformation							ProtocolIE-ID ::= 211
	id-DL-CP-SecurityInformation							ProtocolIE-ID ::= 212
	id-TAI													ProtocolIE-ID ::= 213
	id-UERadioCapabilityForPagingOfNB-IoT					ProtocolIE-ID ::= 214
	id-LTEV2XServicesAuthorized								ProtocolIE-ID ::= 215
	id-NRV2XServicesAuthorized								ProtocolIE-ID ::= 216
	id-LTEUESidelinkAggregateMaximumBitrate					ProtocolIE-ID ::= 217
	id-NRUESidelinkAggregateMaximumBitrate					ProtocolIE-ID ::= 218
	id-PC5QoSParameters										ProtocolIE-ID ::= 219
	id-AlternativeQoSParaSetList							ProtocolIE-ID ::= 220
	id-CurrentQoSParaSetIndex								ProtocolIE-ID ::= 221
	id-CEmodeBrestricted									ProtocolIE-ID ::= 222
 	id-PagingeDRXInformation								ProtocolIE-ID ::= 223
	id-CEmodeBSupport-Indicator								ProtocolIE-ID ::= 224
	id-LTEM-Indication										ProtocolIE-ID ::= 225
	id-EndIndication										ProtocolIE-ID ::= 226
	id-EDT-Session											ProtocolIE-ID ::= 227
	id-UECapabilityInfoRequest								ProtocolIE-ID ::= 228
	id-PDUSessionResourceFailedToResumeListRESReq			ProtocolIE-ID ::= 229
	id-PDUSessionResourceFailedToResumeListRESRes			ProtocolIE-ID ::= 230
	id-PDUSessionResourceSuspendListSUSReq					ProtocolIE-ID ::= 231
	id-PDUSessionResourceResumeListRESReq					ProtocolIE-ID ::= 232
	id-PDUSessionResourceResumeListRESRes					ProtocolIE-ID ::= 233
	id-UE-UP-CIoT-Support									ProtocolIE-ID ::= 234
	id-Suspend-Request-Indication							ProtocolIE-ID ::= 235
	id-Suspend-Response-Indication							ProtocolIE-ID ::= 236
	id-RRC-Resume-Cause										ProtocolIE-ID ::= 237
	id-RGLevelWirelineAccessCharacteristics					ProtocolIE-ID ::= 238
	id-W-AGFIdentityInformation								ProtocolIE-ID ::= 239
	id-GlobalTNGF-ID										ProtocolIE-ID ::= 240
	id-GlobalTWIF-ID										ProtocolIE-ID ::= 241
	id-GlobalW-AGF-ID										ProtocolIE-ID ::= 242
	id-UserLocationInformationW-AGF							ProtocolIE-ID ::= 243
	id-UserLocationInformationTNGF							ProtocolIE-ID ::= 244
	id-AuthenticatedIndication								ProtocolIE-ID ::= 245
	id-TNGFIdentityInformation								ProtocolIE-ID ::= 246
	id-TWIFIdentityInformation								ProtocolIE-ID ::= 247
	id-UserLocationInformationTWIF							ProtocolIE-ID ::= 248
	id-DataForwardingResponseERABList						ProtocolIE-ID ::= 249
	id-IntersystemSONConfigurationTransferDL				ProtocolIE-ID ::= 250
	id-IntersystemSONConfigurationTransferUL				ProtocolIE-ID ::= 251
	id-SONInformationReport									ProtocolIE-ID ::= 252
	id-UEHistoryInformationFromTheUE						ProtocolIE-ID ::= 253
	id-ManagementBasedMDTPLMNList							ProtocolIE-ID ::= 254
	id-MDTConfiguration										ProtocolIE-ID ::= 255
	id-PrivacyIndicator										ProtocolIE-ID ::= 256
	id-TraceCollectionEntityURI								ProtocolIE-ID ::= 257
	id-NPN-Support											ProtocolIE-ID ::= 258
	id-NPN-AccessInformation								ProtocolIE-ID ::= 259
	id-NPN-PagingAssistanceInformation						ProtocolIE-ID ::= 260
	id-NPN-MobilityInformation								ProtocolIE-ID ::= 261
	id-TargettoSource-Failure-TransparentContainer			ProtocolIE-ID ::= 262
	id-NID													ProtocolIE-ID ::= 263
	id-UERadioCapabilityID									ProtocolIE-ID ::= 264
	id-UERadioCapability-EUTRA-Format						ProtocolIE-ID ::= 265
	id-DAPSRequestInfo									ProtocolIE-ID ::= 266
	id-DAPSResponseInfoList								ProtocolIE-ID ::= 267
	id-EarlyStatusTransfer-TransparentContainer 			ProtocolIE-ID ::= 268
	id-NotifySourceNGRANNode									ProtocolIE-ID ::= 269
	id-ExtendedSliceSupportList								ProtocolIE-ID ::= 270
	id-ExtendedTAISliceSupportList							ProtocolIE-ID ::= 271
	id-ConfiguredTACIndication								ProtocolIE-ID ::= 272
	id-Extended-RANNodeName									ProtocolIE-ID ::= 273
	id-Extended-AMFName										ProtocolIE-ID ::= 274
	id-GlobalCable-ID										ProtocolIE-ID ::= 275
	id-QosMonitoringReportingFrequency						ProtocolIE-ID ::= 276
	id-QosFlowParametersList									ProtocolIE-ID ::= 277
	id-QosFlowFeedbackList									ProtocolIE-ID ::= 278
	id-BurstArrivalTimeDownlink								ProtocolIE-ID ::= 279
	id-ExtendedUEIdentityIndexValue							ProtocolIE-ID ::= 280
	id-PduSessionExpectedUEActivityBehaviour					ProtocolIE-ID ::= 281
	id-MicoAllPLMN											ProtocolIE-ID ::= 282
	id-QosFlowFailedToSetupList								ProtocolIE-ID ::= 283

END
-- ASN1STOP

-- ASN1START
-- **************************************************************
--
-- Container definitions
--
-- **************************************************************

NGAP-Containers {
itu-t (0) identified-organization (4) etsi (0) mobileDomain (0) 
ngran-Access (22) modules (3) ngap (1) version1 (1) ngap-Containers (5) }

DEFINITIONS AUTOMATIC TAGS ::= 

BEGIN

-- **************************************************************
--
-- IE parameter types from other modules.
--
-- **************************************************************

IMPORTS

	Criticality,
	Presence,
	PrivateIE-ID,
	ProtocolExtensionID,
	ProtocolIE-ID
FROM NGAP-CommonDataTypes

	maxPrivateIEs,
	maxProtocolExtensions,
	maxProtocolIEs
FROM NGAP-Constants;

-- **************************************************************
--
-- Class Definition for Protocol IEs
--
-- **************************************************************

NGAP-PROTOCOL-IES ::= CLASS {
	&id				ProtocolIE-ID					UNIQUE,
	&criticality	Criticality,
	&Value,
	&presence		Presence
}
WITH SYNTAX {
	ID				&id
	CRITICALITY		&criticality
	TYPE			&Value
	PRESENCE		&presence
}

-- **************************************************************
--
-- Class Definition for Protocol IEs
--
-- **************************************************************

NGAP-PROTOCOL-IES-PAIR ::= CLASS {
	&id					ProtocolIE-ID				UNIQUE,
	&firstCriticality	Criticality,
	&FirstValue,
	&secondCriticality	Criticality,
	&SecondValue,
	&presence			Presence
}
WITH SYNTAX {
	ID						&id
	FIRST CRITICALITY		&firstCriticality
	FIRST TYPE				&FirstValue
	SECOND CRITICALITY		&secondCriticality
	SECOND TYPE				&SecondValue
	PRESENCE				&presence
}

-- **************************************************************
--
-- Class Definition for Protocol Extensions
--
-- **************************************************************

NGAP-PROTOCOL-EXTENSION ::= CLASS {
	&id				ProtocolExtensionID			UNIQUE,
	&criticality	Criticality,
	&Extension,
	&presence		Presence
}
WITH SYNTAX {
	ID				&id
	CRITICALITY		&criticality
	EXTENSION		&Extension
	PRESENCE		&presence
}

-- **************************************************************
--
-- Class Definition for Private IEs
--
-- **************************************************************

NGAP-PRIVATE-IES ::= CLASS {
	&id				PrivateIE-ID,
	&criticality	Criticality,
	&Value,
	&presence		Presence
}
WITH SYNTAX {
	ID				&id
	CRITICALITY		&criticality
	TYPE			&Value
	PRESENCE		&presence
}

-- **************************************************************
--
-- Container for Protocol IEs
--
-- **************************************************************

ProtocolIE-Container {NGAP-PROTOCOL-IES : IEsSetParam} ::= 
	SEQUENCE (SIZE (0..maxProtocolIEs)) OF
	ProtocolIE-Field {{IEsSetParam}}

ProtocolIE-SingleContainer {NGAP-PROTOCOL-IES : IEsSetParam} ::= 
	ProtocolIE-Field {{IEsSetParam}}

ProtocolIE-Field {NGAP-PROTOCOL-IES : IEsSetParam} ::= SEQUENCE {
	id				NGAP-PROTOCOL-IES.&id				({IEsSetParam}),
	criticality		NGAP-PROTOCOL-IES.&criticality		({IEsSetParam}{@id}),
	value			NGAP-PROTOCOL-IES.&Value			({IEsSetParam}{@id})
}

-- **************************************************************
--
-- Container for Protocol IE Pairs
--
-- **************************************************************

ProtocolIE-ContainerPair {NGAP-PROTOCOL-IES-PAIR : IEsSetParam} ::= 
	SEQUENCE (SIZE (0..maxProtocolIEs)) OF
	ProtocolIE-FieldPair {{IEsSetParam}}

ProtocolIE-FieldPair {NGAP-PROTOCOL-IES-PAIR : IEsSetParam} ::= SEQUENCE {
	id					NGAP-PROTOCOL-IES-PAIR.&id					({IEsSetParam}),
	firstCriticality	NGAP-PROTOCOL-IES-PAIR.&firstCriticality	({IEsSetParam}{@id}),
	firstValue			NGAP-PROTOCOL-IES-PAIR.&FirstValue			({IEsSetParam}{@id}),
	secondCriticality	NGAP-PROTOCOL-IES-PAIR.&secondCriticality	({IEsSetParam}{@id}),
	secondValue			NGAP-PROTOCOL-IES-PAIR.&SecondValue			({IEsSetParam}{@id})
}

-- **************************************************************
--
-- Container Lists for Protocol IE Containers
--
-- **************************************************************

ProtocolIE-ContainerList {INTEGER : lowerBound, INTEGER : upperBound, NGAP-PROTOCOL-IES : IEsSetParam} ::=
	SEQUENCE (SIZE (lowerBound..upperBound)) OF
	ProtocolIE-SingleContainer {{IEsSetParam}}

ProtocolIE-ContainerPairList {INTEGER : lowerBound, INTEGER : upperBound, NGAP-PROTOCOL-IES-PAIR : IEsSetParam} ::=
	SEQUENCE (SIZE (lowerBound..upperBound)) OF
	ProtocolIE-ContainerPair {{IEsSetParam}}

-- **************************************************************
--
-- Container for Protocol Extensions
--
-- **************************************************************

ProtocolExtensionContainer {NGAP-PROTOCOL-EXTENSION : ExtensionSetParam} ::= 
	SEQUENCE (SIZE (1..maxProtocolExtensions)) OF
	ProtocolExtensionField {{ExtensionSetParam}}

ProtocolExtensionField {NGAP-PROTOCOL-EXTENSION : ExtensionSetParam} ::= SEQUENCE {
	id					NGAP-PROTOCOL-EXTENSION.&id				({ExtensionSetParam}),
	criticality			NGAP-PROTOCOL-EXTENSION.&criticality	({ExtensionSetParam}{@id}),
	extensionValue		NGAP-PROTOCOL-EXTENSION.&Extension		({ExtensionSetParam}{@id})
}

-- **************************************************************
--
-- Container for Private IEs
--
-- **************************************************************

PrivateIE-Container {NGAP-PRIVATE-IES : IEsSetParam } ::= 
	SEQUENCE (SIZE (1..maxPrivateIEs)) OF
	PrivateIE-Field {{IEsSetParam}}

PrivateIE-Field {NGAP-PRIVATE-IES : IEsSetParam} ::= SEQUENCE {
	id					NGAP-PRIVATE-IES.&id				({IEsSetParam}),
	criticality			NGAP-PRIVATE-IES.&criticality		({IEsSetParam}{@id}),
	value				NGAP-PRIVATE-IES.&Value				({IEsSetParam}{@id})
}

END
-- ASN1STOP
